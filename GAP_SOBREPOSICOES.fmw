FME workspace GAP_SOBREPOSICOES.fmw

Parameters:
- SourceDataset_POSTGIS = 1958_1_SE   # Connection
- FEATURE_TYPES = cb.adm_area_pub_civil_a cb.adm_area_pub_militar_a cb.adm_descontinuidade_geometrica_a cb.adm_descontinuidade_geometrica_p cb.adm_edif_pub_civil_a cb.adm_edif_pub_civil_p cb.adm_edif_pub_militar_a cb.adm_edif_pub_militar_p cb.adm_posto_fiscal_a cb.adm_posto_fiscal_p cb.adm_posto_pol_rod_a cb.adm_posto_pol_rod_p cb.asb_area_abast_agua_a cb.asb_area_saneamento_a cb.asb_cemiterio_a cb.asb_cemiterio_p cb.asb_dep_abast_agua_a cb.asb_dep_abast_agua_p cb.asb_dep_saneamento_a cb.asb_dep_saneamento_p cb.asb_descontinuidade_geometrica_a cb.asb_descontinuidade_geometrica_l cb.asb_descontinuidade_geometrica_p cb.asb_edif_abast_agua_a cb.asb_edif_abast_agua_p cb.asb_edif_saneamento_a cb.asb_edif_saneamento_p cb.aux_descontinuidade_geometrica_a cb.aux_descontinuidade_geometrica_l cb.aux_descontinuidade_geometrica_p cb.eco_area_agrop_ext_veg_pesca_a cb.eco_area_comerc_serv_a cb.eco_area_ext_mineral_a cb.eco_area_industrial_a cb.eco_deposito_geral_a cb.eco_deposito_geral_p cb.eco_descontinuidade_geometrica_a cb.eco_descontinuidade_geometrica_l cb.eco_descontinuidade_geometrica_p cb.eco_edif_agrop_ext_veg_pesca_a cb.eco_edif_agrop_ext_veg_pesca_p cb.eco_edif_comerc_serv_a cb.eco_edif_comerc_serv_p cb.eco_edif_ext_mineral_a cb.eco_edif_ext_mineral_p cb.eco_edif_industrial_a cb.eco_edif_industrial_p cb.eco_equip_agropec_a cb.eco_equip_agropec_l cb.eco_equip_agropec_p cb.eco_ext_mineral_a cb.eco_ext_mineral_p cb.eco_plataforma_a cb.eco_plataforma_p cb.edu_area_ensino_a cb.edu_area_lazer_a cb.edu_area_religiosa_a cb.edu_area_ruinas_a cb.edu_arquibancada_a cb.edu_arquibancada_p cb.edu_campo_quadra_a cb.edu_campo_quadra_p cb.edu_coreto_tribuna_a cb.edu_coreto_tribuna_p cb.edu_descontinuidade_geometrica_a cb.edu_descontinuidade_geometrica_l cb.edu_descontinuidade_geometrica_p cb.edu_edif_const_lazer_a cb.edu_edif_const_lazer_p cb.edu_edif_const_turistica_a cb.edu_edif_const_turistica_p cb.edu_edif_ensino_a cb.edu_edif_ensino_p cb.edu_edif_religiosa_a cb.edu_edif_religiosa_p cb.edu_piscina_a cb.edu_pista_competicao_l cb.edu_ruina_a cb.edu_ruina_p cb.enc_antena_comunic_p cb.enc_area_comunicacao_a cb.enc_area_energia_eletrica_a cb.enc_descontinuidade_geometrica_a cb.enc_descontinuidade_geometrica_p cb.enc_edif_comunic_a cb.enc_edif_comunic_p cb.enc_edif_energia_a cb.enc_edif_energia_p cb.enc_est_gerad_energia_eletr_a cb.enc_est_gerad_energia_eletr_l cb.enc_est_gerad_energia_eletr_p cb.enc_grupo_transformadores_a cb.enc_grupo_transformadores_p cb.enc_hidreletrica_a cb.enc_hidreletrica_l cb.enc_hidreletrica_p cb.enc_ponto_trecho_energia_p cb.enc_termeletrica_a cb.enc_termeletrica_p cb.enc_torre_comunic_p cb.enc_torre_energia_p cb.enc_trecho_comunic_l cb.enc_trecho_energia_l cb.enc_zona_linhas_energia_com_a cb.hid_area_umida_a cb.hid_bacia_hidrografica_a cb.hid_banco_areia_a cb.hid_banco_areia_l cb.hid_barragem_l cb.hid_barragem_p cb.hid_comporta_l cb.hid_comporta_p cb.hid_confluencia_p cb.hid_corredeira_a cb.hid_corredeira_l cb.hid_corredeira_p cb.hid_descontinuidade_geometrica_l cb.hid_descontinuidade_geometrica_p cb.hid_fonte_dagua_p cb.hid_foz_maritima_a cb.hid_foz_maritima_l cb.hid_foz_maritima_p cb.hid_ilha_a cb.hid_ilha_l cb.hid_ilha_p cb.hid_limite_massa_dagua_l cb.hid_natureza_fundo_a cb.hid_natureza_fundo_l cb.hid_natureza_fundo_p cb.hid_ponto_drenagem_p cb.hid_ponto_inicio_drenagem_p cb.hid_quebramar_molhe_a cb.hid_quebramar_molhe_l cb.hid_queda_dagua_a cb.hid_queda_dagua_l cb.hid_queda_dagua_p cb.hid_recife_a cb.hid_recife_l cb.hid_recife_p cb.hid_reservatorio_hidrico_a cb.hid_rocha_em_agua_a cb.hid_rocha_em_agua_p cb.hid_sumidouro_vertedouro_p cb.hid_terreno_suj_inundacao_a cb.hid_trecho_drenagem_l cb.lim_area_de_litigio_a cb.lim_area_desenv_controle_a cb.lim_area_desenv_controle_p cb.lim_area_especial_a cb.lim_area_especial_p cb.lim_area_particular_a cb.lim_area_politico_adm_a cb.lim_area_uso_comunitario_a cb.lim_area_uso_comunitario_p cb.lim_bairro_a cb.lim_delimitacao_fisica_l cb.lim_descontinuidade_geometrica_a cb.lim_descontinuidade_geometrica_p cb.lim_distrito_a cb.lim_limite_area_especial_l cb.lim_limite_intra_munic_adm_l cb.lim_limite_operacional_l cb.lim_limite_particular_l cb.lim_limite_politico_adm_l cb.lim_linha_de_limite_l cb.lim_marco_de_limite_p cb.lim_municipio_a cb.lim_outras_unid_protegidas_a cb.lim_outras_unid_protegidas_p cb.lim_outros_limites_oficiais_l cb.lim_pais_a cb.lim_regiao_administrativa_a cb.lim_sub_distrito_a cb.lim_terra_indigena_a cb.lim_terra_indigena_p cb.lim_terra_publica_a cb.lim_terra_publica_p cb.lim_unidade_conserv_nao_snuc_a cb.lim_unidade_conserv_nao_snuc_p cb.lim_unidade_federacao_a cb.lim_unidade_protecao_integral_a cb.lim_unidade_protecao_integral_p cb.lim_unidade_uso_sustentavel_a cb.lim_unidade_uso_sustentavel_p cb.loc_aglom_rural_de_ext_urbana_p cb.loc_aglomerado_rural_isolado_p cb.loc_aglomerado_rural_p cb.loc_area_habitacional_a cb.loc_area_urbana_isolada_a cb.loc_capital_p cb.loc_cidade_p cb.loc_descontinuidade_geometrica_a cb.loc_descontinuidade_geometrica_l cb.loc_descontinuidade_geometrica_p cb.loc_edif_habitacional_a cb.loc_edif_habitacional_p cb.loc_edificacao_a cb.loc_edificacao_p cb.loc_hab_indigena_a cb.loc_hab_indigena_p cb.loc_localidade_p cb.loc_nome_local_p cb.loc_vila_p cb.pto_area_est_med_fenom_a cb.pto_descontinuidade_geometrica_a cb.pto_descontinuidade_geometrica_p cb.pto_edif_constr_est_med_fen_a cb.pto_edif_constr_est_med_fen_p cb.pto_pto_controle_p cb.pto_pto_est_med_fenomenos_p cb.pto_pto_geod_topo_controle_p cb.pto_pto_ref_geod_topo_p cb.rel_alter_fisiog_antropica_a cb.rel_alter_fisiog_antropica_l cb.rel_curva_batimetrica_l cb.rel_curva_nivel_l cb.rel_descontinuidade_geometrica_a cb.rel_descontinuidade_geometrica_l cb.rel_descontinuidade_geometrica_p cb.rel_dolina_a cb.rel_dolina_p cb.rel_duna_a cb.rel_duna_p cb.rel_elemento_fisiog_natural_a cb.rel_elemento_fisiog_natural_l cb.rel_elemento_fisiog_natural_p cb.rel_gruta_caverna_p cb.rel_pico_p cb.rel_ponto_cotado_altimetrico_p cb.rel_ponto_cotado_batimetrico_p cb.rel_rocha_p cb.sau_area_saude_a cb.sau_area_servico_social_a cb.sau_descontinuidade_geometrica_a cb.sau_descontinuidade_geometrica_p cb.sau_edif_saude_a cb.sau_edif_saude_p cb.sau_edif_servico_social_a cb.sau_edif_servico_social_p cb.tra_area_duto_a cb.tra_area_estrut_transporte_a cb.tra_arruamento_l cb.tra_atracadouro_a cb.tra_atracadouro_l cb.tra_atracadouro_p cb.tra_caminho_aereo_l cb.tra_ciclovia_l cb.tra_condutor_hidrico_l cb.tra_cremalheira_l cb.tra_cremalheira_p cb.tra_descontinuidade_geometrica_a cb.tra_descontinuidade_geometrica_l cb.tra_descontinuidade_geometrica_p cb.tra_eclusa_a cb.tra_eclusa_l cb.tra_eclusa_p cb.tra_edif_constr_aeroportuaria_a cb.tra_edif_constr_aeroportuaria_p cb.tra_edif_constr_portuaria_a cb.tra_edif_constr_portuaria_p cb.tra_edif_metro_ferroviaria_a cb.tra_edif_metro_ferroviaria_p cb.tra_edif_rodoviaria_a cb.tra_edif_rodoviaria_p cb.tra_entroncamento_p cb.tra_faixa_seguranca_a cb.tra_fundeadouro_a cb.tra_fundeadouro_l cb.tra_fundeadouro_p cb.tra_funicular_l cb.tra_funicular_p cb.tra_galeria_bueiro_l cb.tra_galeria_bueiro_p cb.tra_girador_ferroviario_p cb.tra_identific_trecho_rod_p cb.tra_local_critico_a cb.tra_local_critico_l cb.tra_local_critico_p cb.tra_obstaculo_navegacao_a cb.tra_obstaculo_navegacao_l cb.tra_obstaculo_navegacao_p cb.tra_passag_elevada_viaduto_l cb.tra_passag_elevada_viaduto_p cb.tra_passagem_nivel_p cb.tra_patio_a cb.tra_patio_p cb.tra_pista_ponto_pouso_l cb.tra_pista_ponto_pouso_p cb.tra_ponte_l cb.tra_ponte_p cb.tra_ponto_duto_p cb.tra_ponto_ferroviario_p cb.tra_ponto_hidroviario_p cb.tra_ponto_rodoviario_p cb.tra_posto_combustivel_a cb.tra_posto_combustivel_p cb.tra_sinalizacao_p cb.tra_travessia_l cb.tra_travessia_p cb.tra_travessia_pedestre_l cb.tra_travessia_pedestre_p cb.tra_trecho_duto_l cb.tra_trecho_ferroviario_l cb.tra_trecho_hidroviario_l cb.tra_trecho_rodoviario_l cb.tra_trilha_picada_l cb.tra_tunel_l cb.tra_tunel_p cb.veg_descontinuidade_geometrica_l cb.veg_descontinuidade_geometrica_p cb.veg_veg_area_contato_a public.aux_area_a public.aux_linha_l public.aux_objeto_desconhecido_a public.aux_objeto_desconhecido_l public.aux_objeto_desconhecido_p public.aux_ponto_p
- SourceDataset_POSTGIS_5 = 1958_1_SE   # Connection
- FEATURE_TYPES_2 = cb.hid_barragem_a cb.hid_massa_dagua_a cb.hid_trecho_massa_dagua_a cb.loc_area_edificada_a cb.rel_rocha_a cb.rel_terreno_exposto_a cb.tra_pista_ponto_pouso_a cb.veg_brejo_pantano_a cb.veg_caatinga_a cb.veg_campinarana_a cb.veg_cerrado_cerradao_a cb.veg_estepe_a cb.veg_floresta_a cb.veg_macega_chavascal_a cb.veg_mangue_a cb.veg_veg_cultivada_a cb.veg_veg_restinga_a public.aux_area_a public.aux_linha_l public.aux_objeto_desconhecido_a public.aux_objeto_desconhecido_l public.aux_objeto_desconhecido_p public.aux_ponto_p cb.veg_campo_a
- SourceDataset_POSTGIS_4 = 1958_1_SE   # Connection
- FEATURE_TYPES_3 = public.aux_moldura_a

Readers:
- POSTGIS_1: POSTGIS from $(SourceDataset_POSTGIS)
- POSTGIS_2: POSTGIS from $(SourceDataset_POSTGIS_5)
- POSTGIS_3: POSTGIS from $(SourceDataset_POSTGIS_4)

Note: OUTRAS
adm_area_pub_civil_a (reader POSTGIS_1) [off]
    attributes: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
Note: COBERTURA TERRESTRE
hid_barragem_a (reader POSTGIS_2)
    attributes: id int4,PrimaryKey, nome varchar(80), nomeabrev varchar(50), geometriaaproximada int2, matconstr int2, usoprincipal int2, operacional int2, situacaofisica int2, id_complexo_gerad_energ_eletr uuid, reambulado int2, obs varchar(255), cod_folha varchar(80), mid varchar(80), opreambulacao varchar(80), espessuradap float4, datainicioreambulacao date, tiporocha int2, descricao varchar(80), datafimaquisicao date, datainicioedicao1 date, usopista int2, revestimento int2, datainiciovalidacao date, regime int2, datafimvalidacao date, datafimrevaquisicao date, antropizada int2, tipomacchav int2, tipomassadagua int2, engresprevisaoaquisicao varchar(80),
      causaexposicao int2, opedicao2 varchar(80), ocorrenciaem int2, anoaquisicao varchar(80), denso int2, oprevisaoaquisicao varchar(80), datainiciorevaquisicao date, finalidade int2, terreno int2, tipobrejopantano int2, datafimedicao1 date, classe varchar(80), alturamediaindividuos float4, tipoelemnat int2, caracteristicafloresta int2, engrespaquisicao varchar(80), id_trecho_curso_dagua uuid, opaquisicao varchar(80), largura float8, datainicioaquisicao date, oprevisaoreambulacao varchar(80), inom varchar(80), engrespreambulacao varchar(80), classificacaoporte int2, oprevedicao1 varchar(80), datainicioedicao2 date, especiepredominante int2, id_complexo_aeroportuario uuid, datafimedicao2 date, cultivopredominante int2,
      salinidade int2, escala varchar(80), mi varchar(80), datainiciorevedicao1 date, opedicao1 varchar(80), tipocerr int2, datafimreambulacao date, tipotrechomassa int2, extensao float8, datafimrevedicao1 date, tipopista int2, tipocampo int2, tipoterrexp int2, homologacao int2, nomecarta varchar(80), tipolavoura int2, opvalidacao varchar(80), engrespvalidacaoedicao varchar(80), espacamentoindividuos float4
    -> Dissolver
Dissolver
    ACCUM_INPUT_ATTRS = Use Attributes From One Feature
    CLEANING_TOLERANCE = None
    CONNECT_Z_MODE = First Wins
    DEAGGREGATE_INPUT = Yes
    NO_OVRLP = No
    AREA -> Clipper [CLIPPER]
Note: MOLDURA
aux_moldura_a (reader POSTGIS_3)
    attributes: id serial, mi varchar(80), inom varchar(80), escala varchar(80), nomecarta varchar(80), anoaquisicao varchar(80), engrespaquisicao varchar(80), opaquisicao varchar(80), datainicioaquisicao date, datafimaquisicao date, engresprevisaoaquisicao varchar(80), oprevisaoaquisicao varchar(80), datainiciorevaquisicao date, datafimrevaquisicao date, engrespreambulacao varchar(80), opreambulacao varchar(80), datainicioreambulacao date, datafimreambulacao date, oprevisaoreambulacao varchar(80), engrespvalidacaoedicao varchar(80), opvalidacao varchar(80), datainiciovalidacao date, datafimvalidacao date, opedicao1 varchar(80), datainicioedicao1 date, datafimedicao1 date, oprevedicao1 varchar(80), datainiciorevedicao1 date, datafimrevedicao1 date, opedicao2 varchar(80),
      datainicioedicao2 date, datafimedicao2 date
    -> Dissolver_2
Dissolver_2
    ACCUM_INPUT_ATTRS = Use Attributes From One Feature
    CLEANING_TOLERANCE = None
    CONNECT_Z_MODE = First Wins
    DEAGGREGATE_INPUT = Yes
    NO_OVRLP = No
    AREA -> Clipper [CLIPPEE]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> Clipper_Inside_2
Note: BURACOS NA COBERTURA
Clipper_Inside_2: Inspector
