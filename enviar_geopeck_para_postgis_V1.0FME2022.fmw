FME workspace enviar_geopeck_para_postgis_V1.0FME2022.fmw

Parameters:
- SourceDataset_OGCGEOPACKAGE = $(FME_MF_DIR)FORPRON\curvas_recortadas_forpron_2023_bloco_a.gpkg   # GeoPackage File
- DestDataset_POSTGIS = mapeamento_pe_25k_30   # Connection
- SourceDataset_OGCGEOPACKAGE_5 = $(FME_MF_DIR)Projeto Pernambuco\GeoPack\curvas_pernambuco_mapeamento_pe_recortadas.gpkg   # GeoPackage File
- SourceDataset_OGCGEOPACKAGE_4 = $(FME_MF_DIR)Projeto Pernambuco\GeoPack\curvas_pernambuco_mapeamento_pe.gpkg   # GeoPackage File

Readers:
- OGCGEOPACKAGE_1: OGCGEOPACKAGE from $(SourceDataset_OGCGEOPACKAGE)
- OGCGEOPACKAGE_2: OGCGEOPACKAGE from $(SourceDataset_OGCGEOPACKAGE_5)
- OGCGEOPACKAGE_3: OGCGEOPACKAGE from $(SourceDataset_OGCGEOPACKAGE_4)

Writers:
- POSTGIS_1: POSTGIS to $(DestDataset_POSTGIS)

curvas_pernambuco_mapeamento_pe (reader OGCGEOPACKAGE_3)
    attributes: id mediumint, geometriaaproximada boolean, cota mediumint, depressao boolean, tipocurvanivel mediumint, lenght_otf double, length_otf double, fid int,PrimaryKey
    -> curvas_pernambuco_mapeamento_pe_2
curvas_pernambuco_mapeamento_pe_2: Inspector
curvas_pernambuco_mapeamento_pe (reader OGCGEOPACKAGE_2) [off]
    attributes: id mediumint, cota mediumint, mestra text(1), id_0 int,PrimaryKey
    -> edgv.rel_curva_nivel_l (writer POSTGIS_1) [off]
    -> curvas_pernambuco_mapeamento_pe
curvas_pernambuco_mapeamento_pe: Inspector
Curva_Bloco_A1 (reader OGCGEOPACKAGE_1) [off]
    attributes: id mediumint, cota mediumint, mestra text(1), id_0 int,PrimaryKey
    -> Curva_Bloco_A1
    -> Reprojector
Curva_Bloco_A1: Inspector
Reprojector
    DEST = EPSG:4674
    INTERPOLATION_TYPE_NAME = Nearest Neighbor
    RASTER_CELL_SIZE = Preserve Cells
    RASTER_TOLERANCE = 0.0
    REPROJECTED -> edgv.rel_curva_nivel_l (writer POSTGIS_1)
edgv.rel_curva_nivel_l (writer POSTGIS_1)
