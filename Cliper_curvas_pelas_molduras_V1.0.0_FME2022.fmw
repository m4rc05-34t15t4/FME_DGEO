FME workspace Cliper_curvas_pelas_molduras_V1.0.0_FME2022.fmw

Parameters:
- SourceDataset_POSTGIS = FORPRON_2023   # Connection
- DestDataset_OGCGEOPACKAGE = $(FME_MF_DIR)Projeto Pernambuco\GeoPack\curvas_pernambuco_mapeamento_pe_recortadas.gpkg   # GeoPackage File
- SourceDataset_POSTGIS_3 = mapeamento_pe_25k_30   # Connection
- SourceDataset_OGCGEOPACKAGE = $(FME_MF_DIR)Projeto Pernambuco\GeoPack\curvas_pernambuco_mapeamento_pe.gpkg   # GeoPackage File
- DestDataset_POSTGIS = mapeamento_pe_25k_30   # Connection
- SourceDataset_OGCGEOPACKAGE_4 = ""$(FME_MF_DIR)Projeto Pernambuco\Insumos\Bloco A\Curva_Bloco_A1_tratada_e_atributada.gpkg" "$(FME_MF_DIR)Projeto Pernambuco\Insumos\Bloco A\Curva_Bloco_A2_tratada_e_atributada.gpkg""   # GeoPackage File
- SourceDataset_POSTGIS_5 = map_pe_D_E   # Database
- DestDataset_POSTGIS_2 = map_pe_D_E_2   # Database

Readers:
- POSTGIS_1: POSTGIS from $(SourceDataset_POSTGIS)
- POSTGIS_2: POSTGIS from $(SourceDataset_POSTGIS_3)
- OGCGEOPACKAGE_2: OGCGEOPACKAGE from $(SourceDataset_OGCGEOPACKAGE)
- OGCGEOPACKAGE_3: OGCGEOPACKAGE from $(SourceDataset_OGCGEOPACKAGE_4)
- POSTGIS_4: POSTGIS from $(SourceDataset_POSTGIS_5)

Writers:
- OGCGEOPACKAGE_1: OGCGEOPACKAGE to $(DestDataset_OGCGEOPACKAGE)
- POSTGIS_3: POSTGIS to $(DestDataset_POSTGIS)
- POSTGIS_5: POSTGIS to $(DestDataset_POSTGIS_2)

Note: curvas_pernambuco_mapeamento_pe: curvas_pernambuco_mapeamento_pe [OGCGEOPACKAGE]
curvas_pernambuco_mapeamento_pe (reader OGCGEOPACKAGE_2) [off]
    attributes: id mediumint, geometriaaproximada boolean, cota mediumint, depressao boolean, tipocurvanivel mediumint, lenght_otf double, length_otf double, fid int,PrimaryKey
    -> Clipper [CANDIDATE]
    -> curvas_pernambuco_mapeamento_pe
curvas_pernambuco_mapeamento_pe: Inspector
rel_curva_nivel_l (reader POSTGIS_4)
    attributes: id serial, geometriaaproximada bool, cota int4, depressao bool, tipocurvanivel int2
    -> edgv.rel_curva_nivel_l
    -> Clipper [CANDIDATE]
edgv.rel_curva_nivel_l: Inspector
Note: Curva_Bloco_A1: Curva_Bloco_A1_tratada_e_atributada/Curva_Bloco_A2_tratada_e_atributada [OGCGEOPACKAGE]
Curva_Bloco_A1 (reader OGCGEOPACKAGE_3) [off]
    attributes: id mediumint, cota double, geometriaaproximada text(200), depressao text(200), tipocurvanivel text(200), id_0 int,PrimaryKey
    -> Reprojector
Note: edgv.aux_moldura_a: mapeamento_pe_25k_30 [POSTGIS]
aux_moldura_a (reader POSTGIS_2)
    attributes: id serial, escala varchar(255), inom varchar(255), mi varchar(255), nome varchar(80)
    -> Reprojector
Reprojector
    DEST = EPSG:31985
    INTERPOLATION_TYPE_NAME = Nearest Neighbor
    RASTER_CELL_SIZE = Preserve Cells
    RASTER_TOLERANCE = 0.0
    REPROJECTED -> Clipper [CLIPPER]
    REPROJECTED -> edgv.aux_moldura_a
edgv.aux_moldura_a: Inspector
aux_moldura_a (reader POSTGIS_1) [off]
    attributes: id serial,Unique, mi char(10), Revisão varchar(15), Rev_ini date, Rev_fim date, aq_hid varchar(30), data_aq_hid_inicial timestamp, data_aq_hid_final timestamp, aq_plan varchar(30), data_aq_plan_inicial timestamp, data_aq_plan_final timestamp, aq_cob_ter varchar(30), data_aq_cob_ter_inicial timestamp, data_aq_cob_ter_final timestamp, Status varchar(30)
    -> Clipper [CLIPPER]
curva_nivel_l (reader POSTGIS_1) [off]
    attributes: id serial,Unique, cota int4, mestra varchar(1)
    -> Clipper [CANDIDATE]
Clipper
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Deaggregator
    OUTSIDE -> Clipper_Outside
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Clipper_Inside
    DEAGGREGATED -> AttributeKeeper
Clipper_Inside: Inspector
AttributeKeeper
    CREATE_BULK_MODE_FEATURES = NO
    KEEP_ATTRS = cota,mestra,id,depressao,geometriaaproximada,tipocurvanivel
    -> Table1 (writer OGCGEOPACKAGE_1)
    -> CollectionToMulti
Table1 (writer OGCGEOPACKAGE_1) [off]
    attributes: id mediumint, cota mediumint, mestra text(1), geometriaaproximada boolean, depressao boolean, tipocurvanivel mediumint
CollectionToMulti
    -> edgv.rel_curva_nivel_l (writer POSTGIS_3)
    -> edgv.rel_curva_nivel_l (writer POSTGIS_5)
edgv.rel_curva_nivel_l (writer POSTGIS_3) [off]
edgv.rel_curva_nivel_l (writer POSTGIS_5)
Clipper_Outside: Inspector
