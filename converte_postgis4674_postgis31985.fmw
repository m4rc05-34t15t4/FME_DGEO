FME workspace converte_postgis4674_postgis31985.fmw

Parameters:
- SourceDataset_POSTGIS = val_1371-4-SE   # Database
- FEATURE_TYPES = edgv.aux_insumo_externo_a edgv.aux_insumo_externo_l edgv.aux_insumo_externo_p edgv.aux_moldura_a edgv.aux_moldura_area_continua_a edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a
- DestDataset_POSTGIS = edi_1371-4-SE   # Database

Readers:
- POSTGIS_3: POSTGIS from $(SourceDataset_POSTGIS)

Writers:
- POSTGIS_2: POSTGIS to $(DestDataset_POSTGIS)

aux_insumo_externo_a (reader POSTGIS_3)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, atividade_id int4, bitola int2, canteiro_divisorio int2, cod_ponto varchar(255), concessionaria varchar(255), cor varchar(255), corrigido int2, cota int4, cota_comprovada int2, cota_mais_alta int2, creation_time timestamptz, data_fim timestamptz, data_importacao timestamp, data_inicio timestamptz, data_track date,
      densamente_edificada int2, dentro_de_massa_dagua int2, depressao int2, descricao varchar(255), desloc float4, direcao_fixada int2, eletrificada int2, elevation float4, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), json_atividade text, jurisdicao int2, justificativa varchar(255), justificativa_txt int2, label_x float4, label_y float4, largura_simbologia float4, latitude varchar(255), loid oid,Unique, longitude varchar(255),
      material_construcao int2, max_t timestamptz, mi varchar(255), min_t timestamptz, modal_uso int2, nome_usuario varchar(255), nr_faixas varchar(255), nr_linhas int2, nr_pistas varchar(255), oid oid,Unique, operador text, ordem_simbologia int4, orgao_responsavel varchar(255), pageno int4, populacao int4, posicao_pista int2, posicao_relativa int2, posicao_rotulo int2, rank int4, referencial_altim int2, referencial_grav int2, regime int2, revestimento int2, sigla varchar(255), simb_rot float4, sistema_geodesico int2, situacao_em_poligono int2, situacao_fisica int2, situacao_marco int2, sobreposto int2,
      sobreposto_transportes int2, subfase_id int4, sujeito_inundacao int2, suprimir_bandeira int2, suprimir_simbologia int2, tamanho_txt float4, texto_edicao varchar(255), tgattr text, tgconstraint oid,BTREE, tgconstrindid oid, tgconstrrelid oid, tgdeferrable bool, tgenabled char(1), tgfoid oid, tginitdeferred bool, tgisinternal bool, tgname text, tgnargs int2, tgnewtable text, tgoldtable text, tgparentid oid, tgqual text, tgrelid oid,Unique, tgtype int2, tipo int2, tipo_exposicao int2, tipo_produto int2, tipo_ref int2, track_id text, track_segment int4,
      track_segment_point_index int4, trafego int2, uso_pista int2, usuario_uuid uuid, visited bool, visivel int2, vtr text, x_ll float4, y_ll float4
    -> Reprojector
Reprojector
    DEST = EPSG:31985
    INTERPOLATION_TYPE_NAME = Nearest Neighbor
    RASTER_CELL_SIZE = Preserve Cells
    RASTER_TOLERANCE = 0.0
    SOURCE = EPSG:4674
    REPROJECTED -> Table1 (writer POSTGIS_2)
Table1 (writer POSTGIS_2)
