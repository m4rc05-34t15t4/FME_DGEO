FME workspace Preparar_Edicao_EDGV-3.0-PRO_FME-2024.1.3_V2.0.0 _PRODUCAO.fmw

Parameters:
- BD_POSTGIS = ed_utm_1516-3   # Database
- FEATURE_TYPES = edgv.aux_moldura_a edgv.aux_moldura_area_continua_a edgv.aux_observacao_a edgv.aux_observacao_l edgv.aux_observacao_p edgv.aux_reambulacao_a edgv.aux_reambulacao_l edgv.aux_reambulacao_p edgv.aux_revisao_a edgv.aux_revisao_l edgv.aux_revisao_p edgv.centroide_area_edificada_p edgv.centroide_area_sem_dados_p edgv.centroide_elemento_hidrografico_p edgv.centroide_ilha_p edgv.centroide_limite_especial_p edgv.centroide_massa_dagua_p edgv.centroide_vegetacao_p edgv.cobter_area_edificada_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_edificada_l edgv.delimitador_area_sem_dados_l edgv.delimitador_elemento_hidrografico_l edgv.delimitador_limite_especial_l edgv.delimitador_massa_dagua_l edgv.delimitador_vegetacao_l edgv.edicao_borda_elemento_hidrografico_l edgv.edicao_grid_edicao_l edgv.edicao_grid_numerico_p edgv.edicao_identificador_trecho_rod_p edgv.edicao_limite_especial_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_ferrovia_l edgv.infra_mobilidade_urbana_l edgv.infra_obstaculo_vertical_p edgv.infra_pista_pouso_a edgv.infra_pista_pouso_l edgv.infra_pista_pouso_p edgv.infra_travessia_hidroviaria_l edgv.infra_travessia_hidroviaria_p edgv.infra_trecho_duto_l edgv.infra_trecho_hidroviario_l edgv.infra_vala_l edgv.infra_via_deslocamento_l edgv.llp_area_sem_dados_a edgv.llp_limite_especial_a edgv.llp_limite_legal_l edgv.llp_localidade_p edgv.llp_pais_a edgv.llp_ponto_controle_p edgv.llp_unidade_federacao_a
- EPSG = EPSG:31984
- ESCALA = 50
- HOST = 10.46.136.21   # Host
- PORTA = 5432   # Port
- USUARIO = postgres   # Username
- SENHA =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   # Password
- UPDATE = YES
- DestDataset_POSTGIS = r_1291-4-SE   # Database

Readers:
- POSTGIS_1: POSTGIS from $(BD_POSTGIS)

Writers:
- POSTGIS_3: POSTGIS to $(BD_POSTGIS) in $(EPSG)
- POSTGIS_2: POSTGIS to $(DestDataset_POSTGIS)

Note: 10.46.31.21 5432 adminsap / localhost 5433 r_1291-4-SE postgres
aux_insumo_externo_a (reader POSTGIS_1)
    attributes: id uuid, nome varchar(255), fonte varchar(255), observacao varchar(255), operador_criacao varchar(255), data_criacao timestamptz, operador_atualizacao varchar(255), data_atualizacao timestamptz, administracao int2, altitude float4, altitude_geometrica varchar(255), altitude_ortometrica varchar(255), ancora_horizontal int2, ancora_vertical int2, assentamento_precario int2, bitola int2, canteiro_divisorio int2, cod_ponto varchar(255), concessionaria varchar(255), cor varchar(255), corrigido int2, cota int4, cota_comprovada int2, cota_mais_alta int2, densamente_edificada int2, dentro_de_massa_dagua int2, depressao int2, descricao varchar(255), desloc float4, direcao_fixada int2,
      eletrificada int2, em_arruamento int2, espacamento float4, estilo_fonte varchar(255), exibir_lado_simbologia int2, exibir_linha_rotulo int2, exibir_ponta_simbologia int2, exibir_rotulo_aproximado int2, finalidade int2, forma_extracao int2, geometria_aproximada int2, indice int2, inom varchar(255), jurisdicao int2, justificativa varchar(255), justificativa_txt int2, label_x float4, label_y float4, largura_simbologia float4, latitude varchar(255), longitude varchar(255), material_construcao int2, mi varchar(255), modal_uso int2, nr_faixas varchar(255), nr_linhas int2, nr_pistas varchar(255), ordem_simbologia int4, orgao_responsavel varchar(255), populacao int4,
      posicao_pista int2, posicao_relativa int2, posicao_rotulo int2, referencial_altim int2, referencial_grav int2, regime int2, revestimento int2, sigla varchar(255), simb_rot float4, sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_exposicao int2, tipo_produto int2, tipo_ref int2, trafego int2, uso_pista int2, visivel int2
    -> Reprojector
Reprojector
    DEST = $(EPSG)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeManager
AttributeManager
    ATTR_TABLE = SET_TO fme_feature_type (char(50)) = @ReplaceString(@Value(fme_feature_type),"edgv.","",caseSensitive=TRUE)
    -> AttributeFilter
AttributeFilter
    ATTR_NAME = fme_feature_type
    ATTR_VALUES = <Empty>,<Missing>,<Null>,<Unfiltered>,aux_insumo_externo_l,aux_insumo_externo_p,aux_moldura_a,aux_moldura_area_continua_a,aux_reambulacao_a,aux_reambulacao_l,aux_reambulacao_p,aux_revisao_a,aux_revisao_l,aux_revisao_p,aux_validacao_a,aux_validacao_l,aux_validacao_p,centroide_area_construida_p,centroide_area_sem_dados_p,centroide_elemento_hidrografico_p,centroide_ilha_p,centroide_limite_especial_p,centroide_massa_dagua_p,centroide_vegetacao_p,cobter_area_construida_a,cobter_massa_dagua_a,cobter_vegetacao_a,constr_area_uso_especifico_a,constr_deposito_a,constr_deposito_p,constr_edificacao_a,constr_edificacao_p,constr_extracao_mineral_a,constr_extracao_mineral_p,constr_ocupacao_solo_a,constr_ocupacao_solo_l,constr_ocupacao_solo_p,delimitador_area_construida_l,delimitador_area_sem_dados_l,delimitador_elemento_hidrografico_l,delimitador_limite_especial_l,delimitador_massa_dagua_l,delimitador_vegetacao_l,edicao_area_sem_dados_a,edicao_borda_elemento_hidrografico_l,edicao_grid_edicao_l,edicao_identificador_trecho_rod_p,edicao_limite_especial_l,edicao_limite_legal_l,edicao_ponto_mudanca_p,edicao_simb_area_p,edicao_simb_cota_mestra_l,edicao_simb_direcao_corrente_p,edicao_simb_torre_energia_p,edicao_simb_vegetacao_p,edicao_texto_generico_l,edicao_texto_generico_p,elemnat_curva_nivel_l,elemnat_elemento_fisiografico_a,elemnat_elemento_fisiografico_l,elemnat_elemento_fisiografico_p,elemnat_elemento_hidrografico_a,elemnat_elemento_hidrografico_l,elemnat_elemento_hidrografico_p,elemnat_ilha_a,elemnat_ilha_p,elemnat_ponto_cotado_p,elemnat_sumidouro_vertedouro_p,elemnat_terreno_sujeito_inundacao_a,elemnat_toponimo_fisiografico_natural_l,elemnat_toponimo_fisiografico_natural_p,elemnat_trecho_drenagem_l,infra_alteracao_fisiografica_antropica_l,infra_barragem_a,infra_barragem_l,infra_elemento_energia_a,infra_elemento_energia_l,infra_elemento_energia_p,infra_elemento_infraestrutura_a,infra_elemento_infraestrutura_l,infra_elemento_infraestrutura_p,infra_elemento_viario_l,infra_elemento_viario_p,infra_ferrovia_l,infra_mobilidade_urbana_l,infra_pista_pouso_a,infra_pista_pouso_l,infra_pista_pouso_p,infra_travessia_hidroviaria_l,infra_trecho_duto_l,infra_vala_l,infra_via_deslocamento_l,llp_delimitacao_fisica_l,llp_limite_especial_a,llp_localidade_p,llp_pais_a,llp_ponto_controle_p,llp_unidade_federacao_a
    aux_moldura_a -> Junction_7
    aux_moldura_a -> Junction_12
    aux_moldura_a -> Bufferer_7
    aux_moldura_a -> Junction_23
    cobter_vegetacao_a -> Junction_11
    constr_deposito_a -> Junction_4
    constr_deposito_a -> Junction_15
    constr_deposito_p -> Junction_4
    constr_edificacao_a -> Junction_4
    constr_edificacao_a -> Junction_15
    constr_edificacao_p -> Junction_2
    constr_extracao_mineral_a -> Junction_4
    constr_extracao_mineral_a -> Junction_15
    constr_extracao_mineral_p -> Junction_4
    constr_ocupacao_solo_a -> Junction_4
    constr_ocupacao_solo_l -> Junction_4
    constr_ocupacao_solo_p -> Junction_4
    delimitador_area_construida_l -> Junction_4
    delimitador_massa_dagua_l -> Junction_4
    delimitador_vegetacao_l -> Junction_4
    elemnat_curva_nivel_l -> Junction_4
    elemnat_ilha_a -> Junction_4
    elemnat_ponto_cotado_p -> Junction_3
    elemnat_sumidouro_vertedouro_p -> Junction_4
    elemnat_trecho_drenagem_l -> Junction_4
    elemnat_trecho_drenagem_l -> Junction_6
    elemnat_trecho_drenagem_l -> AttributeCreator_14
    infra_alteracao_fisiografica_antropica_l -> Junction_4
    infra_barragem_a -> Junction_4
    infra_barragem_l -> Junction_4
    infra_elemento_energia_a -> Junction_4
    infra_elemento_energia_l -> Junction_4
    infra_elemento_energia_p -> Junction_4
    infra_elemento_infraestrutura_a -> Junction_4
    infra_elemento_infraestrutura_l -> Junction_4
    infra_elemento_infraestrutura_p -> Junction_4
    infra_elemento_viario_p -> Junction_8
    infra_ferrovia_l -> Junction_4
    infra_ferrovia_l -> Tester_12
    infra_pista_pouso_a -> Junction_4
    infra_pista_pouso_l -> Junction_4
    infra_pista_pouso_p -> Junction_4
    infra_trecho_duto_l -> Junction_4
    infra_vala_l -> Junction_4
    infra_via_deslocamento_l -> Junction
    infra_via_deslocamento_l -> Junction_4
    infra_via_deslocamento_l -> Junction_9
    infra_via_deslocamento_l -> Junction_10
    infra_via_deslocamento_l -> Junction_19
    infra_via_deslocamento_l -> Tester_11
Junction_15
    -> Junction_14
VertexCreator_4 [off]
    MEASURE_TYPE_LOOKUP = CONTINUOUS
    MODE = REPLACE
    XVAL = @Value(label_x)
    YVAL = @Value(label_y)
    MEASURE_TYPE = Continuous
    MODE_NAME = Replace with Point
    -> VertexCreator_4_Output
VertexCreator_4_Output: Inspector
Junction_6
    -> Definir_Tamanho_Txt_Linhas [Feature_Entrada]
Definir_Tamanho_Txt_Linhas [off]
    ID = @Value(id)
    NOME = @Value(nome)
    Feature_Saida -> Trecho_Drenagem
    Feature_Saida -> Junction_19
Junction_19 [off]
    -> Junction_14 [off]
Trecho_Drenagem: Inspector [off]
Junction_21
    -> Junction_14
CollectionToMulti_2
    -> Table100 (writer POSTGIS_3)
Table100 (writer POSTGIS_3)
Junction_22
    -> Junction_24
Junction_24
    -> CollectionToMulti
    -> ALL
ALL: Inspector
CollectionToMulti
    -> Table1 (writer POSTGIS_3)
Table1 (writer POSTGIS_3)
    attributes: visivel varchar(200), id uuid

Bookmark: Criar centroids_vegetação
Junction_11 [off]
    -> AttributeKeeper_8 [off]
AttributeKeeper_8 [off]
    CREATE_BULK_MODE_FEATURES = NO
    KEEP_ATTRS = fme_feature_type,tipo
    -> Dissolver [off]
Dissolver [off]
    ACCUM_INPUT_ATTRS = Use Attributes From One Feature
    CLEANING_TOLERANCE_LOOKUP = AUTO
    CONNECT_Z_MODE_LOOKUP = FIRST_WINS
    DEAGGREGATE_INPUT = Yes
    GROUP_BY = tipo
    CLEANING_TOLERANCE = Automatic
    CONNECT_Z_MODE = First Wins
    AREA -> Counter_2 [off]
Counter_2 [off]
    CNT_ATTR = _id_area
    DOMAIN = counter
    SCOPE = Global
    START = 1
    -> AttributeCreator_7 [off]
AttributeCreator_7 [off]
    ATTR_TABLE:
      SET_TO _area (varchar(200)) = @Area()
      SET_TO _densidade (real64) = @Evaluate(@ceil(@Value(_area) / (4 * (4 * $(ESCALA) * 10) ** 2) ,0))
    -> Cobertura_Terrestre [off]
    -> CenterlineReplacer [off]
Cobertura_Terrestre: Inspector [off]
    TACKATTRS = tipo
CenterlineReplacer [off]
    MODE = APPROX_CENTER_LINE
    CENTERLINE -> AttributeCreator_8 [off]
AttributeCreator_8 [off]
    ATTR_TABLE = SET_TO _comprimento (varchar(200)) = @Length()
    -> Bufferer_4 [off]
Bufferer_4 [off]
    ANGLE = 22.5
    CAP_STYLE_LOOKUP = CAP_ARC
    CORNER_STYLE_LOOKUP = JOIN_ARC
    MODE = AREA
    OFFSET = 1
    OFFSET_UNITS = METERS
    PRECISION = APPROX
    CAP_STYLE = Arc
    CORNER_STYLE = Arc
    BUFFERED -> Dissolver_2 [off]
Dissolver_2 [off]
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Tester_8 [off]
Tester_8 [off]
    BOOL_OP = OR
    TEST_CLAUSE = TEST @Value(_densidade) > 1
    TEST_MODE = TEST
    PASSED -> Clipper [CANDIDATE] [off]
    FAILED -> Deaggregator [off]
Junction_12 [off]
    -> Clipper_2 [CLIPPER] [off]
Junction_13 [off]
    -> 2DGridAccumulator_3 [off]
2DGridAccumulator_3 [off]
    BBOX_TYPE = GRID_POLYGONS
    COL_ATTR = _column
    GRID_ORIGIN = TOP_LEFT
    ROW_ATTR = _row
    SIZE_TYPE = Cell Size
    XINC = $(ESCALA) * 10 * 4 * 2
    XSEED = @Value(_x_min_grid)
    YINC = $(ESCALA) * 10 * 4 * 2
    YSEED = @Value(_y_max_grid)
    GRID_TYPE = Polygons
    STARTINGCORNER = Upper Left
    GRID -> Clipper_2 [CANDIDATE] [off]
Clipper_2 [off]
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeCreator_9 [off]
AttributeCreator_9 [off]
    ATTR_TABLE:
      SET_TO _area (varchar(200)) = @Area()
      SET_TO _id_grid_4x (varchar(200)) = @Value(_column)_@Value(_row)
    -> Tester_9 [off]
    -> Grid_4x [off]
Grid_4x: Inspector [off]
Tester_9 [off]
    BOOL_OP = OR
    TEST_CLAUSE = TEST @Value(_area) > @Evaluate((($(ESCALA) * 10 * 4) ** 2) * 2)
    TEST_MODE = TEST
    PASSED -> Clipper [CLIPPER] [off]
Clipper [off]
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator [off]
Deaggregator [off]
    ATTR_ACCUM_MODE = Merge List Attributes
    ATTR_CONFLICT_RES_LOOKUP = INCOMING_IF_CONFLICT
    EXPLODE_INSTANCES = No
    GEOM_NAME_FIELD = _geometry_name
    LIST_ATTR_MODE_LOOKUP = LEAN
    PART_NUMBER_FIELD = _part_number
    RECURSIVE = No
    SPLIT_COMPOSITES = No
    ATTR_CONFLICT_RES = Use List Attribute Values
    MODE = Flatten One Level
    DEAGGREGATED -> Counter [off]
Counter [off]
    CNT_ATTR = _id
    DOMAIN = counter
    SCOPE = Global
    START = 1
    -> AttributeCreator_10 [off]
AttributeCreator_10 [off]
    ATTR_TABLE:
      SET_TO _area_2 (real64) = @Evaluate(@Area())
      SET_TO _idgrid_area (varchar(200)) = @Value(_id_grid_4x)_@Value(_id_area)
    -> Sorter_2 [off]
Sorter_2 [off]
    SORT_PARM = _idgrid_area NUMERIC ASCENDING _area_2 NUMERIC DESCENDING
    SORTED -> ModuloCounter_2 [off]
ModuloCounter_2 [off]
    CNT_ATTR = _modulo_count
    DOMAIN = @Value(_idgrid_area)
    MOD = 99999
    -> Tester_10 [off]
Tester_10 [off]
    BOOL_OP = COMPOSITE
    COMPOSITE_TEST = 1 OR ( 2 AND 3 )
    TEST_CLAUSE:
      TEST @Value(_modulo_count) = 0
      TEST @Value(_area_2) >= 2000.0
      TEST @Value(_modulo_count) > 0
    TEST_MODE = TEST
    PASSED -> CenterPointReplacer [off]
    PASSED -> NeighborFinder_2 [CANDIDATE] [off]
    PASSED -> Center_line_Cobter [off]
CenterPointReplacer [off]
    POINTTYPE = CENTER
    POINT -> NeighborFinder_2 [BASE] [off]
NeighborFinder_2 [off]
    CANDIDATES_FIRST = No
    GROUP_BY = _id
    INSERT_VERTEX = No
    K = 1
    MEASURES_FROM_CANDIDATE = Yes
    MEASURE_TYPE = Continuous
    MODE = Bases and Candidates
    TREAT_POLYGON_AS = Lines
    MATCHED -> VertexCreator_2 [off]
VertexCreator_2 [off]
    MEASURE_TYPE_LOOKUP = CONTINUOUS
    MODE = REPLACE
    XVAL = @Value(_closest_candidate_x)
    YVAL = @Value(_closest_candidate_y)
    MEASURE_TYPE = Continuous
    MODE_NAME = Replace with Point
    -> Bufferer_5 [off]
    -> AttributeKeeper_10 [off]
Bufferer_5 [off]
    ANGLE = 22.5
    CAP_STYLE_LOOKUP = CAP_ROUND
    CORNER_STYLE_LOOKUP = JOIN_ROUND
    MODE = AREA
    OFFSET = 50
    OFFSET_UNITS = METERS
    PRECISION = APPROX
    CAP_STYLE = Round
    CORNER_STYLE = Round
    BUFFERED -> Centroides_CobTer [off]
Centroides_CobTer: Inspector [off]
AttributeKeeper_10 [off]
    CREATE_BULK_MODE_FEATURES = NO
    KEEP_ATTRS = tipo
    -> AttributeCreator_11 [off]
AttributeCreator_11 [off]
    ATTR_TABLE = SET_TO fme_feature_type (varchar(20)) = centroid_vegetacao_p
    -> Pontos_Centroides [off]
Pontos_Centroides: Inspector [off]
Center_line_Cobter: Inspector [off]

Bookmark: Grid
Junction_7
    -> BoundsExtractor
BoundsExtractor
    XMAX = _xmax
    XMIN = _xmin
    YMAX = _ymax
    YMIN = _ymin
    ZMAX = _zmax
    ZMIN = _zmin
    -> AttributeCreator_4
AttributeCreator_4
    ATTR_TABLE:
      SET_TO _x_min_grid (real64) = @Evaluate(@mult(@floor(@div(@Value(_xmin),1000.0),0),1000))
      SET_TO _y_max_grid (real64) = @Evaluate(@mult(@ceil(@div(@Value(_ymax),1000.0),0),1000))
    -> 2DGridAccumulator_2
    -> Junction_13
2DGridAccumulator_2
    BBOX_TYPE = GRID_POLYGONS
    COL_ATTR = _column
    GRID_ORIGIN = TOP_LEFT
    ROW_ATTR = _row
    SIZE_TYPE = Cell Size
    XINC = $(ESCALA) * 10 * 4
    XSEED = @Value(_x_min_grid)
    YINC = $(ESCALA) * 10 * 4
    YSEED = @Value(_y_max_grid)
    GRID_TYPE = Polygons
    STARTINGCORNER = Upper Left
    GRID -> AttributeCreator_5
AttributeCreator_5
    ATTR_TABLE:
      SET_TO fme_feature_type (varchar(12)) = linhas_gride
      SET_TO id_celular_grid (varchar(200)) = @Value(_row)_@Value(_column)
    -> Grid
    -> Junction_4
    -> AttributeKeeper_19
Grid: Inspector

Bookmark: Ocultar Cotas
AttributeKeeper_19
    CREATE_BULK_MODE_FEATURES = NO
    KEEP_ATTRS = id_celular_grid
    -> PointOnAreaOverlayer_2 [AREA]
PointOnAreaOverlayer_2
    ATTR_ACCUM_MODE = Merge Incoming
    ATTR_CONFLICT_RES_LOOKUP = ORIGINAL_IF_CONFLICT
    CANDIDATE_LIST_ATTRS_TO_INCLUDE = _peso _qtd_agreg cota cota_mais_alta id
    CANDIDATE_LIST_ATTRS_TO_INCLUDE_MODE_LU = SELECTED
    CANDIDATE_LIST_NAME = pontos_cotados
    DEAGGREGATE_INPUT = Yes
    OV_ATTR = qtd_cotas_agregadas
    POLYS_FIRST = NO
    ATTR_CONFLICT_RES = Use Original
    CANDIDATE_LIST_ATTRS_TO_INCLUDE_MODE = Selected Attributes
    POINT -> Sorter_4
Sorter_4
    GROUP_BY = id_celular_grid
    SORT_PARM = cota NUMERIC DESCENDING _qtd_agreg NUMERIC ASCENDING _peso NUMERIC ASCENDING
    SORTED -> ModuloCounter_3
ModuloCounter_3
    CNT_ATTR = _modulo_count
    DOMAIN = @Value(id_celular_grid)
    MOD = 1000
    -> AttributeCreator_20
AttributeCreator_20
    ATTR_TABLE = SET_TO visivel (varchar(200)) = FME_CONDITIONAL:DEFAULT_VALUE'2'BOOL_OP;OR;COMPOSITE_TEST;1 OR 2;TEST @Value(_modulo_count) <= 3;TEST @Value(cota_mais_alta) = 1'1'FME_NUM_CONDITIONS2___
    -> AttributeKeeper_20
AttributeKeeper_20
    CREATE_BULK_MODE_FEATURES = NO
    KEEP_ATTRS = ancora_horizontal,ancora_vertical,cota,cota_mais_alta,fme_feature_type,id,label_x,label_y,visivel
    -> Junction_24

Bookmark: Rotacionar Edificações com base nas rodovias
Junction
    -> Chopper
Chopper
    DEAGGREGATE_INPUT = Deaggregate
    MAX_VERTICES = 2
    MODE_LOOKUP = VERTEX
    REMNANT_ATTR = _remnant
    MODE = By Vertex
    CHOPPED -> NeighborFinder [CANDIDATE]
Junction_2
    -> NeighborFinder [BASE]
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> AttributeCreator_13
    UNMATCHED_CANDIDATE -> AttributeKeeper_2
AttributeCreator_13
    ATTR_TABLE:
      SET_TO rotacao (varchar(200)) = @Value(_angle)
      SET_TO _largura_edif (real64) = @Evaluate((0.2 + 1) * $(ESCALA) / 2)
      SET_TO _x_original (varchar(200)) = @Value(_closest_base_x)
      SET_TO _y_original (varchar(200)) = @Value(_closest_base_y)
    -> AttributeKeeper
AttributeKeeper
    CREATE_BULK_MODE_FEATURES = NO
    KEEP_ATTRS = fme_feature_type,id,_angle,_candidate_angle,_candidate_label_angle,_closest_base_x,_closest_base_y,_closest_candidate_x,_closest_candidate_y,_distance,_largura_edif,rotacao,_x_original,_y_original
    -> Bufferer
    -> Junction_16
Bufferer
    ANGLE = 22.5
    CAP_STYLE_LOOKUP = CAP_PROJECTING
    CORNER_STYLE_LOOKUP = JOIN_MITER
    MITER_LIMIT = 1
    MODE = AREA
    OFFSET = @Value(_largura_edif)
    OFFSET_UNITS = METERS
    PRECISION = APPROX
    CAP_STYLE = Square
    CORNER_STYLE = Miter
    BUFFERED -> Rotator
Rotator
    ANGLE = @Value(rotacao)
    XORIG = @Value(_x_original)
    YORIG = @Value(_y_original)
    ROTATED -> Edificações_Rotacionadas
Edificações_Rotacionadas: Inspector
AttributeKeeper_2
    CREATE_BULK_MODE_FEATURES = NO
    KEEP_ATTRS = fme_feature_type,id
    -> Rodovias_Segmentadas
Rodovias_Segmentadas: Inspector

Bookmark: Afastar Edificações nas Linhas
Junction_16
    -> AttributeKeeper_11
AttributeKeeper_11
    CREATE_BULK_MODE_FEATURES = NO
    KEEP_ATTRS = fme_feature_type,id,_x_original,_y_original,rotacao,_largura_edif
    -> NeighborFinder_3 [BASE]
Junction_14
    -> AttributeCreator_12
AttributeCreator_12
    ATTR_TABLE = SET_TO _largura (varchar(200)) = FME_CONDITIONAL:DEFAULT_VALUE'@Evaluate((0.2 + 0.2) * $(ESCALA) / 2)'BOOL_OP;OR;COMPOSITE_TEST;1;TEST @Value(fme_feature_type) = infra_via_deslocamento_l'@Evaluate((0.2 + 0.3) * $(ESCALA) / 2)'BOOL_OP;OR;COMPOSITE_TEST;1;TEST @Value(fme_feature_type) = elemnat_trecho_drenagem_l'@Evaluate((0.2 + 0.2) * $(ESCALA) / 2)'BOOL_OP;OR;COMPOSITE_TEST;1;TEST @Right(@Value(fme_feature_type),2) = _a'@Evaluate((0.2) * $(ESCALA) / 2)'FME_NUM_CONDITIONS4___
    -> Bufferer_6
Bufferer_6
    ANGLE = 22.5
    CAP_STYLE_LOOKUP = CAP_PROJECTING
    CORNER_STYLE_LOOKUP = JOIN_MITER
    MITER_LIMIT = 1
    MODE = AREA
    OFFSET = @Value(_largura)
    OFFSET_UNITS = METERS
    PRECISION = APPROX
    CAP_STYLE = Square
    CORNER_STYLE = Miter
    BUFFERED -> Linhas_buffers
    BUFFERED -> AttributeKeeper_12
    BUFFERED -> Junction_17
    BUFFERED -> Junction_20 [off]
AttributeKeeper_12
    CREATE_BULK_MODE_FEATURES = NO
    KEEP_ATTRS = fme_feature_type,id
    -> NeighborFinder_3 [CANDIDATE]
    -> PointOnAreaOverlayer [AREA]
NeighborFinder_3
    CANDIDATES_FIRST = No
    INSERT_VERTEX = No
    K = 1
    MAX = (0.2 + 1) * $(ESCALA) / 2 * 1.5
    MEASURES_FROM_CANDIDATE = Yes
    MEASURE_TYPE = Continuous
    MODE = Bases and Candidates
    TREAT_POLYGON_AS = Lines
    MATCHED -> VertexCreator
    MATCHED -> PointOnAreaOverlayer [POINT]
    UNMATCHED_BASE -> Box_edficacao_rotacionado [Bufferer_7_Input]
PointOnAreaOverlayer
    DEAGGREGATE_INPUT = Yes
    OV_ATTR = _overlaps
    POLYS_FIRST = NO
    POINT -> Offsetter
Offsetter
    AZIMUTH_2D = 180
    MODE_LOOKUP = POLAR
    RADIUS_2D = FME_CONDITIONAL:DEFAULT_VALUE'@Value(_largura_edif) - @Value(_distance)'BOOL_OP;OR;COMPOSITE_TEST;1;TEST @Value(_overlaps) > 0'@Value(_largura_edif) + @Value(_distance)'FME_NUM_CONDITIONS2___
    MODE = Polar Coordinate
    OFFSET -> Box_edficacao_rotacionado [Bufferer_7_Input]
Box_edficacao_rotacionado
    ROTACAO = @Value(rotacao)
    _LARGURA_EDIF = @Value(_largura_edif)
    _X_ORIGINAL = @Value(_x_original)
    _Y_ORIGINAL = @Value(_y_original)
    Rotator_2_Rotated -> AttributeKeeper_18
AttributeKeeper_18
    CREATE_BULK_MODE_FEATURES = NO
    KEEP_ATTRS = _largura_edif,_x_original,_y_original,fme_feature_type,id,rotacao
    -> Box_edf_rot
    -> AttributeCreator_15
    -> AttributeCreator_26 [off]
Box_edf_rot: Inspector
VertexCreator
    MEASURE_TYPE_LOOKUP = CONTINUOUS
    MODE = REPLACE
    XVAL = @Value(_closest_base_x)
    YVAL = @Value(_closest_base_y)
    MEASURE_TYPE = Continuous
    MODE_NAME = Replace with Point
    -> VertexCreator_3
VertexCreator_3
    ALLOW_DUPLICATES = YES
    CLOSE_LINES = Yes
    MEASURE_TYPE_LOOKUP = CONTINUOUS
    MISSING_VAL_MODE_LOOKUP = COMPUTE_NANS
    MODE = ADD
    XVAL = @Value(_closest_candidate_x)
    YVAL = @Value(_closest_candidate_y)
    IGNORE_DUPLICATES = No
    MEASURE_TYPE = Continuous
    MISSING_VAL_MODE = Compute
    MODE_NAME = Add Point
    -> Linha_Deslocamento
Linha_Deslocamento: Inspector
Linhas_buffers: Inspector

Bookmark: Grid Ponto Cotado e arrendodamento de Cota
Junction_3
    -> AttributeKeeper_3
    -> FeatureMerger [REQUESTOR]
AttributeKeeper_3
    CREATE_BULK_MODE_FEATURES = NO
    KEEP_ATTRS = fme_feature_type,id
    -> Bufferer_2
Bufferer_2
    ANGLE = 22.5
    CAP_STYLE_LOOKUP = CAP_PROJECTING
    CORNER_STYLE_LOOKUP = JOIN_MITER
    MITER_LIMIT = 1
    MODE = AREA
    OFFSET = $(ESCALA) * 4
    OFFSET_UNITS = METERS
    PRECISION = APPROX
    CAP_STYLE = Square
    CORNER_STYLE = Miter
    BUFFERED -> 2DGridAccumulator
    BUFFERED -> 2DGridAccumulator_4
    BUFFERED -> Agregar_elementos_box [Area]
2DGridAccumulator
    BBOX_TYPE = GRID_POLYGONS
    COL_ATTR = _column
    GRID_ORIGIN = TOP_LEFT
    GROUP_BY = id
    ROW_ATTR = _row
    SIZE_TYPE = Number of Cells
    XCOUNT = 2
    YCOUNT = 8
    GRID_TYPE = Polygons
    STARTINGCORNER = Upper Left
    GRID -> AttributeCreator_16
AttributeCreator_16
    ATTR_TABLE = SET_TO nr_box_grid (varchar(200)) = FME_CONDITIONAL:DEFAULT_VALUE'_FME_NO_OP_'BOOL_OP;COMPOSITE;COMPOSITE_TEST;( 1 AND 2 ) OR ( 3 AND 4 );TEST @Value(_row) = 1;TEST @Value(_column) = 0;TEST @Value(_row) = 2;TEST @Value(_column) = 0'4'BOOL_OP;COMPOSITE;COMPOSITE_TEST;( 1 AND 2 ) OR ( 3 AND 4 );TEST @Value(_row) = 3;TEST @Value(_column) = 0;TEST @Value(_row) = 4;TEST @Value(_column) = 0'5'BOOL_OP;COMPOSITE;COMPOSITE_TEST;( 1 AND 2 ) OR ( 3 AND 4 );TEST @Value(_row) = 5;TEST @Value(_column) = 0;TEST @Value(_row) = 6;TEST @Value(_column) = 0'6'BOOL_OP;COMPOSITE;COMPOSITE_TEST;( 1 AND 2 ) OR ( 3 AND 4 );TEST @Value(_row) = 1;TEST @Value(_column) = 1;TEST @Value(_row) = 2;TEST @Value(_column) = 1'1'BOOL_OP;COMPOSITE;COMPOSITE_TEST;( 1 AND 2 ) OR ( 3 AND 4 );TEST @Value(_row) = 3;TEST @Value(_column) = 1;TEST @Value(_row) = 4;TEST @Value(_column) = 1'2'BOOL_OP;COMPOSITE;COMPOSITE_TEST;( 1 AND 2 ) OR ( 3 AND 4 );TEST @Value(_row) = 5;TEST @Value(_column) = 1;TEST @Value(_row) = 6;TEST @Value(_column) = 1'3'FME_NUM_CONDITIONS7___
    -> Tester
2DGridAccumulator_4
    BBOX_TYPE = GRID_POLYGONS
    COL_ATTR = _column
    GRID_ORIGIN = TOP_LEFT
    GROUP_BY = id
    ROW_ATTR = _row
    SIZE_TYPE = Number of Cells
    XCOUNT = 4
    YCOUNT = 8
    GRID_TYPE = Polygons
    STARTINGCORNER = Upper Left
    GRID -> AttributeCreator_17
AttributeCreator_17
    ATTR_TABLE = SET_TO nr_box_grid (varchar(200)) = FME_CONDITIONAL:DEFAULT_VALUE'_FME_NO_OP_'BOOL_OP;COMPOSITE;COMPOSITE_TEST;( 1 AND 2 ) OR ( 3 AND 4 ) OR ( 5 AND 6 ) OR ( 7 AND 8 );TEST @Value(_row) = 1;TEST @Value(_column) = 1;TEST @Value(_row) = 1;TEST @Value(_column) = 2;TEST @Value(_row) = 2;TEST @Value(_column) = 1;TEST @Value(_row) = 2;TEST @Value(_column) = 2'7'BOOL_OP;COMPOSITE;COMPOSITE_TEST;( 1 AND 2 ) OR ( 3 AND 4 ) OR ( 5 AND 6 ) OR ( 7 AND 8 );TEST @Value(_row) = 3;TEST @Value(_column) = 1;TEST @Value(_row) = 3;TEST @Value(_column) = 2;TEST @Value(_row) = 4;TEST @Value(_column) = 1;TEST @Value(_row) = 4;TEST @Value(_column) = 2'9'BOOL_OP;COMPOSITE;COMPOSITE_TEST;( 1 AND 2 ) OR ( 3 AND 4 ) OR ( 5 AND 6 ) OR ( 7 AND 8 );TEST @Value(_row) = 5;TEST @Value(_column) = 1;TEST @Value(_row) = 5;TEST @Value(_column) = 2;TEST @Value(_row) = 6;TEST @Value(_column) = 1;TEST @Value(_row) = 6;TEST @Value(_column) = 2'8'FME_NUM_CONDITIONS4___
    -> Tester
Tester
    BOOL_OP = OR
    TEST_CLAUSE = TEST nr_box_grid ATTRIBUTE_HAS_A_VALUE ""
    TEST_MODE = TEST
    PASSED -> Dissolver_3
Dissolver_3
    ACCUM_INPUT_ATTRS = Drop Incoming Attributes
    CLEANING_TOLERANCE_LOOKUP = AUTO
    CONNECT_Z_MODE_LOOKUP = FIRST_WINS
    DEAGGREGATE_INPUT = Yes
    GROUP_BY = nr_box_grid id
    CLEANING_TOLERANCE = Automatic
    CONNECT_Z_MODE = First Wins
    AREA -> Offsetter_3
Offsetter_3
    MODE_LOOKUP = CARTESIAN
    XOFF = FME_CONDITIONAL:DEFAULT_VALUE'0'BOOL_OP;OR;COMPOSITE_TEST;1 OR 2 OR 3;TEST @Value(nr_box_grid) = 1;TEST @Value(nr_box_grid) = 2;TEST @Value(nr_box_grid) = 3'$(ESCALA) / 25 * 7.5'BOOL_OP;OR;COMPOSITE_TEST;1 OR 2 OR 3;TEST @Value(nr_box_grid) = 4;TEST @Value(nr_box_grid) = 5;TEST @Value(nr_box_grid) = 6'$(ESCALA) / 25 * 7.5 * -1'FME_NUM_CONDITIONS3___
    YOFF = 0
    ZOFF = 0
    MODE = Cartesian Coordinate
    OFFSET -> AttributeCreator
AttributeCreator
    ATTR_TABLE:
      SET_TO fme_feature_type (varchar(17)) = grid_ponto_cotado
      SET_TO posicao_nr (varchar(200)) = @Value(nr_box_grid)
      SET_TO id_ponto_cotado (varchar(200)) = @Value(id)
      SET_TO id (buffer) = @Value(id)_@Value(posicao_nr)
    -> Intersector
    -> AttributeFilter_2
AttributeFilter_2
    ATTR_NAME = posicao_nr
    ATTR_VALUES = <Empty>,<Missing>,<Null>,<Unfiltered>,1,2,3,4,5,6,7,8,X
    1 -> Agregar_elementos_box_1 [Area]
    2 -> Agregar_elementos_box_2 [Area]
    3 -> Agregar_elementos_box_3 [Area]
    4 -> Agregar_elementos_box_4 [Area]
    5 -> Agregar_elementos_box_5 [Area]
    6 -> Agregar_elementos_box_6 [Area]
    7 -> Agregar_elementos_box_7 [Area]
    8 -> Agregar_elementos_box_8 [Area]
    X -> Agregar_elementos_box_9 [Area]
Bufferer_7
    ANGLE = 22.5
    CAP_STYLE_LOOKUP = CAP_PROJECTING
    CORNER_STYLE_LOOKUP = JOIN_MITER
    MITER_LIMIT = 1
    MODE = AREA
    OFFSET = $(ESCALA) * 1
    OFFSET_UNITS = METERS
    PRECISION = APPROX
    CAP_STYLE = Square
    CORNER_STYLE = Miter
    BUFFERED -> Bufferer_8
    BUFFERED -> Junction_23
Bufferer_8
    ANGLE = 22.5
    CAP_STYLE_LOOKUP = CAP_PROJECTING
    CORNER_STYLE_LOOKUP = JOIN_BEVEL
    MODE = AREA
    OFFSET = $(ESCALA) * 2
    OFFSET_UNITS = METERS
    PRECISION = APPROX
    CAP_STYLE = Square
    CORNER_STYLE = Bevel
    BUFFERED -> Junction_23
Junction_23
    -> Junction_4
Junction_4
    -> Intersector
Intersector
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> Agregar_elementos_box [Elementos]
Agregar_elementos_box
    FME_FEATURE_TYPE = @Value(fme_feature_type)
    ID = @Value(id)
    -> Junction_5
Junction_5
    -> Agregar_elementos_box_1 [Elementos]
    -> Agregar_elementos_box_2 [Elementos]
    -> Agregar_elementos_box_3 [Elementos]
    -> Agregar_elementos_box_4 [Elementos]
    -> Agregar_elementos_box_5 [Elementos]
    -> Agregar_elementos_box_6 [Elementos]
    -> Agregar_elementos_box_7 [Elementos]
    -> Agregar_elementos_box_8 [Elementos]
    -> Agregar_elementos_box_9 [Elementos]
Agregar_elementos_box_1
    FME_FEATURE_TYPE = @Value(fme_feature_type)
    ID = @Value(id)
    -> Junction_18
Agregar_elementos_box_2
    FME_FEATURE_TYPE = @Value(fme_feature_type)
    ID = @Value(id)
    -> Junction_18
Agregar_elementos_box_3
    FME_FEATURE_TYPE = @Value(fme_feature_type)
    ID = @Value(id)
    -> Junction_18
Agregar_elementos_box_4
    FME_FEATURE_TYPE = @Value(fme_feature_type)
    ID = @Value(id)
    -> Junction_18
Agregar_elementos_box_5
    FME_FEATURE_TYPE = @Value(fme_feature_type)
    ID = @Value(id)
    -> Junction_18
Agregar_elementos_box_6
    FME_FEATURE_TYPE = @Value(fme_feature_type)
    ID = @Value(id)
    -> Junction_18
Agregar_elementos_box_7
    FME_FEATURE_TYPE = @Value(fme_feature_type)
    ID = @Value(id)
    -> Junction_18
Agregar_elementos_box_8
    FME_FEATURE_TYPE = @Value(fme_feature_type)
    ID = @Value(id)
    -> Junction_18
Agregar_elementos_box_9 [off]
    FME_FEATURE_TYPE = @Value(fme_feature_type)
    ID = @Value(id)
    -> Junction_18
Junction_18
    -> Peso
Peso: AttributeCreator
    ATTR_TABLE = SET_TO _peso (varchar(200)) = FME_CONDITIONAL:DEFAULT_VALUE'@Evaluate(0)'BOOL_OP;OR;COMPOSITE_TEST;1;TEST @Value(fme_feature_type) = elemnat_curva_nivel_l'@Evaluate(15 * @Length())'BOOL_OP;OR;COMPOSITE_TEST;1;TEST @Value(fme_feature_type) = infra_via_deslocamento_l'@Evaluate(20 * @Length())'BOOL_OP;OR;COMPOSITE_TEST;1;TEST @Value(fme_feature_type) = elemnat_trecho_drenagem_l'@Evaluate(25 * @Length())'BOOL_OP;OR;COMPOSITE_TEST;1;TEST @Right(@Value(fme_feature_type),2) = _p'@Evaluate(10)'BOOL_OP;OR;COMPOSITE_TEST;1;TEST @Right(@Value(fme_feature_type),2) = _l'@Evaluate(10 * @Length())'BOOL_OP;OR;COMPOSITE_TEST;1;TEST @Value(fme_feature_type) = grid_ponto_cotado'@Evaluate(5 * @Length())'BOOL_OP;OR;COMPOSITE_TEST;1;TEST @Value(fme_feature_type) = linhas_grid'@Evaluate(5 * @Length())'FME_NUM_CONDITIONS8___
    -> Aggregator
Aggregator
    ACCUM_ATTRS_NAME = Drop Incoming Attributes
    AGGREGATE_TYPE = Homogeneous Collection (If Possible)
    COUNT_ATTR = _qtd_agreg
    GROUP_BY = GRID_id
    MODE = Geometry - Assemble One Level
    SEP = ,
    SUM = _peso
    AGGREGATE -> AttributeCreator_2
AttributeCreator_2
    ATTR_TABLE:
      SET_TO id_ponto_cotado (varchar(200)) = @Left(@Value(GRID_id),36)
      SET_TO nr_posicao (varchar(200)) = @Right(@Value(GRID_id),1)
    -> Sorter
Sorter
    GROUP_BY = id_ponto_cotado
    SORT_PARM = _peso NUMERIC ASCENDING _qtd_agreg NUMERIC ASCENDING id_ponto_cotado ALPHA ASCENDING
    SORTED -> ModuloCounter
ModuloCounter
    CNT_ATTR = _modulo_count
    DOMAIN = @Value(id_ponto_cotado)
    MOD = 9
    -> Tester_2
    -> Box_grid_All
Tester_2
    BOOL_OP = OR
    TEST_CLAUSE = TEST @Value(_modulo_count) = 0
    TEST_MODE = TEST
    PASSED -> AttributeKeeper_4
AttributeKeeper_4
    CREATE_BULK_MODE_FEATURES = NO
    KEEP_ATTRS = _peso,_qtd_agreg,id_ponto_cotado,nr_posicao
    -> Box_Grid_agregado
    -> FeatureMerger [SUPPLIER]
FeatureMerger
    ATTR_ACCUM_MODE = Merge Supplier
    ATTR_CONFLICT_RES_LOOKUP = REQUESTOR_IF_CONFLICT
    IGNORE_NULLS = No
    JOIN_KEYS = @Value(id) @Value(id_ponto_cotado) STRING
    MERGE_TYPE = Attributes Only
    PROCESS_DUPS = NO
    REJECT_NULL_MISSING_KEYS = No
    SUPPLIERS_FIRST = No
    ATTR_CONFLICT_RES = Use Requestor
    MERGED -> Sorter_3
Sorter_3
    SORT_PARM = cota NUMERIC DESCENDING
    SORTED -> Counter_3
Counter_3
    CNT_ATTR = _count
    DOMAIN = counter
    SCOPE = Global
    START = 0
    -> CoordinateExtractor_3
CoordinateExtractor_3
    IND = 0
    RECURSIVE = No
    X_ATTR = _x
    Y_ATTR = _y
    MODE = Specify Coordinate
    -> AttributeCreator_3
AttributeCreator_3
    ATTR_TABLE:
      SET_TO cota (int32) = FME_CONDITIONAL:DEFAULT_VALUE'@round(@Value(cota),0)'BOOL_OP;OR;COMPOSITE_TEST;1;TEST @FindString(@Value(cota),9.,0,caseSensitive=TRUE) >= 0'@floor(@Value(cota),0)'BOOL_OP;OR;COMPOSITE_TEST;1;TEST @FindString(@Value(cota),0.,0,caseSensitive=TRUE) >= 0'@ceil(@Value(cota),0)'FME_NUM_CONDITIONS3___
      SET_TO ancora_horizontal (int16) = FME_CONDITIONAL:DEFAULT_VALUE'_FME_NO_OP_'BOOL_OP;OR;COMPOSITE_TEST;1 OR 2 OR 3;TEST @Value(nr_posicao) = 1;TEST @Value(nr_posicao) = 2;TEST @Value(nr_posicao) = 3'1'BOOL_OP;OR;COMPOSITE_TEST;1 OR 2;TEST @Value(nr_posicao) = 7;TEST @Value(nr_posicao) = 8'2'BOOL_OP;OR;COMPOSITE_TEST;1 OR 2 OR 3;TEST @Value(nr_posicao) = 4;TEST @Value(nr_posicao) = 5;TEST @Value(nr_posicao) = 6'3'FME_NUM_CONDITIONS4___
      SET_TO ancora_vertical (int16) = FME_CONDITIONAL:DEFAULT_VALUE'_FME_NO_OP_'BOOL_OP;OR;COMPOSITE_TEST;1 OR 2 OR 3;TEST @Value(nr_posicao) = 1;TEST @Value(nr_posicao) = 7;TEST @Value(nr_posicao) = 4'1'BOOL_OP;OR;COMPOSITE_TEST;1 OR 2;TEST @Value(nr_posicao) = 2;TEST @Value(nr_posicao) = 5'2'BOOL_OP;OR;COMPOSITE_TEST;1 OR 2 OR 3;TEST @Value(nr_posicao) = 3;TEST @Value(nr_posicao) = 8;TEST @Value(nr_posicao) = 6'3'FME_NUM_CONDITIONS4___
      SET_TO cota_mais_alta (int16) = FME_CONDITIONAL:DEFAULT_VALUE'2'BOOL_OP;OR;COMPOSITE_TEST;1;TEST @Value(_count) = 0'1'FME_NUM_CONDITIONS2___
      SET_TO label_x (real32) = FME_CONDITIONAL:DEFAULT_VALUE'@Value(_x)'BOOL_OP;OR;COMPOSITE_TEST;1 OR 2 OR 3;TEST @Value(nr_posicao) = 1;TEST @Value(nr_posicao) = 2;TEST @Value(nr_posicao) = 3'@Evaluate(($(ESCALA) / 25 * 7.5) + @Value(_x))'BOOL_OP;OR;COMPOSITE_TEST;1 OR 2;TEST @Value(nr_posicao) = 7;TEST @Value(nr_posicao) = 8'@Value(_x)'BOOL_OP;OR;COMPOSITE_TEST;1 OR 2 OR 3;TEST @Value(nr_posicao) = 4;TEST @Value(nr_posicao) = 5;TEST @Value(nr_posicao) = 6'@Evaluate(($(ESCALA) / 25 * 7.5 * -1) + @Value(_x))'FME_NUM_CONDITIONS4___
      SET_TO label_y (real32) = FME_CONDITIONAL:DEFAULT_VALUE'@Value(_y)'BOOL_OP;OR;COMPOSITE_TEST;1 OR 2 OR 3;TEST @Value(nr_posicao) = 1;TEST @Value(nr_posicao) = 7;TEST @Value(nr_posicao) = 4'@Evaluate(($(ESCALA) * 2)  + @Value(_y))'BOOL_OP;OR;COMPOSITE_TEST;1 OR 2;TEST @Value(nr_posicao) = 2;TEST @Value(nr_posicao) = 5'@Value(_y)'BOOL_OP;OR;COMPOSITE_TEST;1 OR 2 OR 3;TEST @Value(nr_posicao) = 3;TEST @Value(nr_posicao) = 8;TEST @Value(nr_posicao) = 6'@Evaluate(($(ESCALA) * 2 * -1)  + @Value(_y))'FME_NUM_CONDITIONS4___
    -> Ponto_Cotado_Posicao
    -> AttributeKeeper_16
    -> VertexCreator_4
Ponto_Cotado_Posicao: Inspector
Note: 4 / 7 / 1 / 5 / X / 2 / 6 / 8 / 3
AttributeKeeper_16
    CREATE_BULK_MODE_FEATURES = NO
    KEEP_ATTRS = id,fme_feature_type,cota,cota_mais_alta,ancora_horizontal,ancora_vertical,label_x,label_y,_peso,_qtd_agreg
    -> Junction_24
    -> PointOnAreaOverlayer_2 [POINT]
Box_Grid_agregado: Inspector
Box_grid_All: Inspector

Bookmark: Arruamento
Tester_11
    BOOL_OP = OR
    TEST_CLAUSE = TEST @Value(tipo) = 5
    TEST_MODE = TEST
    PASSED -> Junction_21
    PASSED -> AttributeCreator_18
    FAILED -> Junction_21
AttributeCreator_18
    ATTR_TABLE:
      SET_TO nr_faixas (varchar(255)) = 1
      SET_TO nr_pistas (varchar(255)) = 1
    -> AttributeKeeper_14
AttributeKeeper_14
    CREATE_BULK_MODE_FEATURES = NO
    KEEP_ATTRS = fme_feature_type,id,nr_faixas,nr_pistas
    -> Junction_22

Bookmark: Ferrovia
Tester_12
    BOOL_OP = OR
    TEST_CLAUSE = TEST @Value(eletrificada) != 1
    TEST_MODE = TEST
    PASSED -> AttributeCreator_19
AttributeCreator_19
    ATTR_TABLE = SET_TO eletrificada (int16) = 2
    -> AttributeKeeper_17
AttributeKeeper_17
    CREATE_BULK_MODE_FEATURES = NO
    KEEP_ATTRS = eletrificada,fme_feature_type,id
    -> Junction_22

Bookmark: Tamanhos texto Rios
AttributeCreator_14
    ATTR_TABLE:
      SET_TO _escala (varchar(200)) = $(ESCALA)
      SET_TO regime (int16) = FME_CONDITIONAL:DEFAULT_VALUE'@Value(regime)'BOOL_OP;OR;COMPOSITE_TEST;1;TEST @Value(tipo) = 3'3'FME_NUM_CONDITIONS2___
    -> Definir_Tamanho_Txt_Linhas_2 [Feature_Entrada]
Definir_Tamanho_Txt_Linhas_2
    ID = @Value(id)
    NOME = @Value(nome)
    Feature_Saida -> Trecho_Drenagem_2
    Feature_Saida -> AttributeKeeper_13
Trecho_Drenagem_2: Inspector
AttributeKeeper_13
    CREATE_BULK_MODE_FEATURES = NO
    KEEP_ATTRS = fme_feature_type,id,tamanho_txt,regime
    -> Junction_22
    -> Junction_21

Bookmark: novo afastar e oculatr
Junction_20 [off]
    -> teste_loop_displace_edif [VariableSetter_Input] [off]
    -> teste_loop_displace_edif_2 [VariableSetter_Input] [off]
    -> teste_loop_displace_edif_3 [VariableSetter_Input] [off]
AttributeCreator_26 [off]
    ATTR_TABLE:
      SET_TO _visivel (uint8)
      SET_TO _movido (uint8) = 0
    -> GeometryExtractor_2 [off]
GeometryExtractor_2 [off]
    ATTR = _geometry_original
    KIND = fmebinary
    REMOVE_GEOMETRY = No
    KIND_LONG = FME Binary
    -> CenterPointReplacer_3 [off]
CenterPointReplacer_3 [off]
    POINTTYPE = CENTER
    POINT -> teste_loop_displace_edif [VariableSetter_Input] [off]
teste_loop_displace_edif [off]
    FME_FEATURE_TYPE = @Value(fme_feature_type)
    ID = @Value(id)
    ROTACAO = @Value(rotacao)
    _GEOMETRY_ORIGINAL = @Value(_geometry_original)
    _LARGURA_EDIF = @Value(_largura_edif)
    _MOVIDO = @Value(_movido)
    _VISIVEL = @Value(_visivel)
    _X_ORIGINAL = @Value(_x_original)
    _Y_ORIGINAL = @Value(_y_original)
    -> 1_1 [off]
    Output_2 -> 1_2 [off]
    Output_2 -> teste_loop_displace_edif_3 [VariableSetter_Input] [off]
1_1: Inspector [off]
1_2: Inspector [off]
teste_loop_displace_edif_3 [off]
    FME_FEATURE_TYPE = @Value(fme_feature_type)
    ID = @Value(id)
    ROTACAO = @Value(rotacao)
    _GEOMETRY_ORIGINAL = @Value(_geometry_original)
    _LARGURA_EDIF = @Value(_largura_edif)
    _MOVIDO = @Value(_movido)
    _VISIVEL = @Value(_visivel)
    _X_ORIGINAL = @Value(_x_original)
    _Y_ORIGINAL = @Value(_y_original)
    -> 1_5 [off]
    Output_2 -> 1_6 [off]
    Output_2 -> teste_loop_displace_edif_2 [VariableSetter_Input] [off]
    Output_2 -> Box_edficacao_rotacionado_4 [Bufferer_7_Input] [off]
Box_edficacao_rotacionado_4 [off]
    ROTACAO = @Value(rotacao)
    _LARGURA_EDIF = @Value(_largura_edif)
    _X_ORIGINAL = @Value(_x_original)
    _Y_ORIGINAL = @Value(_y_original)
    Rotator_2_Rotated -> casa_2 [off]
casa_2: Inspector [off]
    TACKATTRS = _visivel
1_5: Inspector [off]
1_6: Inspector [off]
teste_loop_displace_edif_2 [off]
    FME_FEATURE_TYPE = @Value(fme_feature_type)
    ID = @Value(id)
    ROTACAO = @Value(rotacao)
    _GEOMETRY_ORIGINAL = @Value(_geometry_original)
    _LARGURA_EDIF = @Value(_largura_edif)
    _MOVIDO = @Value(_movido)
    _VISIVEL = @Value(_visivel)
    _X_ORIGINAL = @Value(_x_original)
    _Y_ORIGINAL = @Value(_y_original)
    -> Box_edficacao_rotacionado_2 [Bufferer_7_Input] [off]
    Output_2 -> 1_4 [off]
Box_edficacao_rotacionado_2 [off]
    ROTACAO = @Value(rotacao)
    _LARGURA_EDIF = @Value(_largura_edif)
    _X_ORIGINAL = @Value(_x_original)
    _Y_ORIGINAL = @Value(_y_original)
    Rotator_2_Rotated -> 1_3 [off]
1_3: Inspector [off]
    TACKATTRS = _visivel
1_4: Inspector [off]

Bookmark: Ocultar Edificacoes
AttributeCreator_15
    ATTR_TABLE = SET_TO _visivel (varchar(200))
    -> GeometryExtractor
GeometryExtractor
    ATTR = _geometry_original
    KIND = fmebinary
    REMOVE_GEOMETRY = No
    KIND_LONG = FME Binary
    -> CenterPointReplacer_2
CenterPointReplacer_2
    POINTTYPE = CENTER
    POINT -> Junction_17
Junction_17
    -> Loop_Configurar_Visibilidade_Edificacoes [Edificacoes_Linahs_Buffers]
Loop_Configurar_Visibilidade_Edificacoes
    FME_FEATURE_TYPE = @Value(fme_feature_type)
    ID = @Value(id)
    NOME = @Value(nome)
    ROTACAO = @Value(rotacao)
    TIPO = @Value(tipo)
    _GEOMETRY_ORIGINAL = @Value(_geometry_original)
    _LARGURA_EDIF = @Value(_largura_edif)
    _VISIVEL = @Value(_visivel)
    _X_ORIGINAL = @Value(_x_original)
    _Y_ORIGINAL = @Value(_y_original)
    -> AttributeCreator_22
AttributeCreator_22
    ATTR_TABLE = SET_TO visivel (varchar(200)) = FME_CONDITIONAL:DEFAULT_VALUE'2'BOOL_OP;OR;COMPOSITE_TEST;1 OR 2;TEST @Value(_visivel) = 1;TEST @Value(_visivel) = 3'1'FME_NUM_CONDITIONS2___
    -> AttributeKeeper_15
    -> GeometryReplacer
GeometryReplacer
    KIND = fmebinary
    REMOVE_ATTRIBUTE = Yes
    SOURCE = @Value(_geometry_original)
    KIND_LONG = FME Binary
    -> Edificacoes_Visualizacao
Edificacoes_Visualizacao: Inspector
    TACKATTRS = _visivel
AttributeKeeper_15
    CREATE_BULK_MODE_FEATURES = NO
    KEEP_ATTRS = id,visivel,fme_feature_type
    -> Junction_24 [off]
    -> CollectionToMulti_2
    -> ALL

Bookmark: Rotacionar elementos com base direção de Linhas
Junction_9 [off]
    -> LineCombiner [off]
    -> via [off]
via: Inspector [off]
LineCombiner [off]
    ACCUM_ATTRS_NAME = Use Attributes From One Feature
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> PointOnLineOverlayer [LINE] [off]
Junction_8 [off]
    -> Bufferer_3 [off]
    -> PointOnLineOverlayer [POINT] [off]
    -> pontos [off]
    -> CoordinateExtractor_2 [off]
    -> FeatureMerger_2 [REQUESTOR] [off]
PointOnLineOverlayer [off]
    DEAGGREGATE_INPUT = Yes
    MEASURE_TYPE_LOOKUP = CONTINUOUS
    MERGE_MEASURES = Yes
    OV_ATTR = _overlaps
    TOLERANCE = 5
    MEASURE_TYPE = Continuous
    LINE -> Tester_3 [off]
Tester_3 [off]
    BOOL_OP = OR
    TEST_CLAUSE = TEST @Value(_overlaps) > 0
    TEST_MODE = TEST
    PASSED -> Intersector_2 [off]
CoordinateExtractor_2 [off]
    IND = 0
    RECURSIVE = No
    X_ATTR = _x
    Y_ATTR = _y
    MODE = Specify Coordinate
    -> AttributeKeeper_5 [off]
AttributeKeeper_5 [off]
    CREATE_BULK_MODE_FEATURES = NO
    KEEP_ATTRS = fme_feature_type,id,_x,_y
    -> PointOnLineOverlayer_2 [POINT] [off]
Bufferer_3 [off]
    ANGLE = 22.5
    CAP_STYLE_LOOKUP = CAP_ARC
    CORNER_STYLE_LOOKUP = JOIN_ARC
    MODE = AREA
    OFFSET = 15
    OFFSET_UNITS = METERS
    PRECISION = APPROX
    CAP_STYLE = Arc
    CORNER_STYLE = Arc
    BUFFERED -> Intersector_2 [off]
Intersector_2 [off]
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> AttributeKeeper_6 [off]
AttributeKeeper_6 [off]
    CREATE_BULK_MODE_FEATURES = NO
    KEEP_ATTRS = fme_feature_type,id
    -> PointOnLineOverlayer_2 [LINE] [off]
PointOnLineOverlayer_2 [off]
    ATTR_ACCUM_MODE = Prefix Incoming
    DEAGGREGATE_INPUT = Yes
    INCOMING_PREFIX = pontos_
    MEASURE_TYPE_LOOKUP = CONTINUOUS
    MERGE_MEASURES = Yes
    OV_ATTR = _overlaps
    TOLERANCE = 3
    MEASURE_TYPE = Continuous
    LINE -> Tester_4 [off]
Tester_4 [off]
    BOOL_OP = OR
    TEST_CLAUSE = TEST @Value(_overlaps) > 0
    TEST_MODE = TEST
    PASSED -> LineCombiner_2 [off]
LineCombiner_2 [off]
    ACCUM_ATTRS_NAME = Use Attributes From One Feature
    BREAK_CONNECTION_ATTRIBUTES = pontos_fme_feature_type pontos_id
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = END_NODED
    PRESERVE = no
    BREAK = no
    CONNECT_Z_MODE = First Wins
    CONSIDER_NODE_ELEVATION = no
    TOPOLOGY = End Noded
    LINE -> VertexCounter [off]
VertexCounter [off]
    CNT_ATTR = _vertexcount
    -> Tester_5 [off]
Tester_5 [off]
    BOOL_OP = OR
    TEST_CLAUSE = TEST @Value(_vertexcount) > 2
    TEST_MODE = TEST
    PASSED -> VertexRemover [off]
    FAILED -> CoordinateExtractor [off]
VertexRemover [off]
    IND = 1
    KEEP_REMOVE = REMOVE
    LEN = @Value(_vertexcount) - 2
    KEEP_REMOVE_PARAM = Remove
    -> CoordinateExtractor [off]
CoordinateExtractor [off]
    LIST_NAME = _indices
    RECURSIVE = Yes
    MODE = All Coordinates
    -> AttributeCreator_6 [off]
AttributeCreator_6 [off]
    ATTR_TABLE = SET_TO simb_rot (varchar(200)) = FME_CONDITIONAL:DEFAULT_VALUE'@Evaluate(@fmod(( ( @atan2(( @Value(_indices{1}.x) - @Value(_indices{0}.x) ), ( @Value(_indices{1}.y) - @Value(_indices{0}.y) ) ) * 180 / @pi() ) + 360.0 ), 360.0))'BOOL_OP;OR;COMPOSITE_TEST;1;TEST @Evaluate(@Value(_indices{1}.x) - @Value(_indices{0}.x)) = 0'0'FME_NUM_CONDITIONS2___
    -> Rotator_3 [off]
    -> AttributeKeeper_7 [off]
Rotator_3 [off]
    ANGLE = @Value(simb_rot)
    XORIG = @Value(pontos__x)
    YORIG = @Value(pontos__y)
    ROTATED -> Elementos_Rotacionados [off]
Elementos_Rotacionados: Inspector [off]
AttributeKeeper_7 [off]
    CREATE_BULK_MODE_FEATURES = NO
    KEEP_ATTRS = pontos__x,pontos__y,pontos_id,simb_rot,pontos_fme_feature_type
    -> FeatureMerger_2 [SUPPLIER] [off]
FeatureMerger_2 [off]
    ATTR_ACCUM_MODE = Merge Supplier
    ATTR_CONFLICT_RES_LOOKUP = SUPPLIER_IF_CONFLICT
    IGNORE_NULLS = No
    JOIN_KEYS = @Value(fme_feature_type) @Value(pontos_fme_feature_type) AUTO @Value(id) @Value(pontos_id) AUTO
    MERGE_TYPE = Attributes Only
    PROCESS_DUPS = NO
    REJECT_NULL_MISSING_KEYS = No
    SUPPLIERS_FIRST = No
    ATTR_CONFLICT_RES = Use Supplier
    MERGED -> Pontos_Com_Rotação [off]
    <REJECTED> -> Pontos_Com_Rotação_erro [off]
Pontos_Com_Rotação: Inspector [off]
Pontos_Com_Rotação_erro: Inspector [off]
pontos: Inspector [off]

Bookmark: Obter Pontos Mudança Atributos
Junction_10 [off]
    -> Intersector_3 [off]
Intersector_3 [off]
    ATTRS_ACCUM_MODE = Use Attributes From One Feature
    CLEANING_TOLERANCE_LOOKUP = 3
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = 3
    DUPLICATE_Z_NODES = No
    MEASURE_TYPE = Continuous
    INTERSECTED -> PointOnLineOverlayer_3 [LINE] [off]
    INTERSECTED -> Vias [off]
    NODE -> AttributeKeeper_9 [off]
Vias: Inspector [off]
AttributeKeeper_9 [off]
    CREATE_BULK_MODE_FEATURES = NO
    KEEP_ATTRS = fme_feature_type,id,nr_faixas
    -> PointOnLineOverlayer_3 [POINT] [off]
PointOnLineOverlayer_3 [off]
    ATTR_ACCUM_MODE = Merge Incoming
    ATTR_CONFLICT_RES_LOOKUP = ORIGINAL_IF_CONFLICT
    DEAGGREGATE_INPUT = Yes
    LIST_ATTRS_TO_INCLUDE = fme_feature_type id nr_faixas
    LIST_NAME = _vias
    MEASURE_TYPE_LOOKUP = CONTINUOUS
    MERGE_MEASURES = Yes
    OV_ATTR = _overlaps
    TOLERANCE = 3
    ATTR_CONFLICT_RES = Use Original
    MEASURE_TYPE = Continuous
    POINT -> Tester_6 [off]
Tester_6 [off]
    BOOL_OP = OR
    TEST_CLAUSE = TEST @Value(_overlaps) = 2
    TEST_MODE = TEST
    PASSED -> ListConcatenator_2 [off]
ListConcatenator_2 [off]
    DROP_EMPTY_PARTS = Yes
    LIST_ATTR = _vias{}.id
    SEP = ,
    VAL_ATTR = _concatenated_ids
    -> ListConcatenator [off]
ListConcatenator [off]
    DROP_EMPTY_PARTS = Yes
    LIST_ATTR = _vias{}.nr_faixas
    SEP = ,
    VAL_ATTR = _concatenated
    -> PythonCaller [off]
PythonCaller [off]
    HIDE_ATTRIBUTES = _segments administracao altitude altitude_geometrica altitude_ortometrica ancora_horizontal ancora_vertical assentamento_precario bitola canteiro_divisorio cod_ponto concessionaria cor corrigido cota cota_comprovada cota_mais_alta data_atualizacao data_criacao densamente_edificada dentro_de_massa_dagua depressao descricao desloc direcao_fixada eletrificada em_arruamento espacamento estilo_fonte exibir_lado_simbologia exibir_linha_rotulo exibir_ponta_simbologia exibir_rotulo_aproximado finalidade fme_feature_type fonte forma_extracao geometria_aproximada id indice inom jurisdicao justificativa justificativa_txt label_x label_y largura_simbologia latitude longitude material_construcao mi modal_uso nome nr_faixas nr_linhas nr_pistas observacao operador_atualizacao operador_criacao ordem_simbologia orgao_responsavel populacao posicao_pista posicao_relativa posicao_rotulo referencial_altim referencial_grav regime revestimento sigla simb_rot sistema_geodesico situacao_em_poligono situacao_fisica situacao_marco sobreposto sobreposto_transportes subfase_id sujeito_inundacao suprimir_bandeira suprimir_simbologia tamanho_txt texto_edicao tipo tipo_exposicao tipo_produto tipo_ref trafego uso_pista visivel
    LIST_ATTRS = _vias{} _vias{}.fme_feature_type _vias{}.id _vias{}.nr_faixas
    NEW_ATTRIBUTES = add_ponto varchar(3)
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              nr_faixa = None
              add_ponto = "NAO"
              for i in feature.getAttribute('_concatenated').split(","):
                  if nr_faixa == None and i != None:
                      nr_faixa = i
                  elif i != None and nr_faixa != i:
                      add_ponto = "SIM"

              feature.setAttribute("add_ponto", add_ponto)

              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> Tester_7 [off]
Tester_7 [off]
    BOOL_OP = OR
    TEST_CLAUSE = TEST @Value(add_ponto) = SIM
    TEST_MODE = TEST
    PASSED -> Pontos_Mudança_TRA [off]
Pontos_Mudança_TRA: Inspector [off]

FME custom transformer teste_loop_ocultar_edif

Parameters:
- _GEOMETRY_ORIGINAL = @Value(_geometry_original)   # Geometry Original
- FME_FEATURE_TYPE = @Value(fme_feature_type)   # Fme Feature Type
- ID = @Value(id)   # id
- _LARGURA_EDIF = @Value(_largura_edif)   # Largura Edif
- _X_ORIGINAL = @Value(_x_original)   # X Original
- _Y_ORIGINAL = @Value(_y_original)   # Y Original
- ROTACAO = @Value(rotacao)   # rotacao
- _VISIVEL = @Value(_visivel)   # Visivel

Deaggregator_2_Input (input)
    -> AttributeCreator_4
AttributeCreator_4
    ATTR_TABLE = SET_TO _loop (uint8) = 1
    -> GeometryFilter_2
GeometryFilter_2
    FILTER_MODE = SIMPLE
    FILTER_MULTI = FILTER_TYPES]"Point Area"]FME_CONTROLLER_QUERY_FILE]]FME_CONTROLLER_CHOICE]Simple
    Point -> Tester_5
    Area -> AttributeKeeper_2
    Area -> Junction_2
Tester_5
    BOOL_OP = OR
    TEST_CLAUSE = TEST _visivel ATTRIBUTE_HAS_A_VALUE ""
    TEST_MODE = TEST
    PASSED -> Junction_2
    FAILED -> GeometryReplacer_4
Junction_2
    -> FeatureMerger_3 [REQUESTOR]
GeometryReplacer_4
    KIND = fmebinary
    REMOVE_ATTRIBUTE = No
    SOURCE = @Value(_geometry_original)
    KIND_LONG = FME Binary
    -> AttributeKeeper_2
    -> AttributeKeeper_4
AttributeKeeper_4
    CREATE_BULK_MODE_FEATURES = NO
    KEEP_ATTRS = _largura_edif,_x_original,_y_original,fme_feature_type,id,rotacao,_visivel,_geometry_original,_loop
    -> PointOnAreaOverlayer_6 [AREA]
AttributeKeeper_2
    CREATE_BULK_MODE_FEATURES = NO
    KEEP_ATTRS = fme_feature_type,id,_loop
    -> AreaOnAreaOverlayer_2 [AREA]
AreaOnAreaOverlayer_2
    ACCUM_ATTRS_NAME = Drop Incoming Attributes
    CLEANING_TOLERANCE_LOOKUP = 0
    CONNECT_Z_MODE_LOOKUP = FIRST_WINS
    DEAGGREGATE_INPUT = Yes
    OVC_ATTR = _overlaps_areas
    CLEANING_TOLERANCE = 0
    CONNECT_Z_MODE = First Wins
    AREA -> Tester_2
Tester_2
    BOOL_OP = OR
    TEST_CLAUSE = TEST @Value(_overlaps_areas) > 1
    TEST_MODE = TEST
    PASSED -> AttributeCreator_2
AttributeCreator_2
    ATTR_TABLE = SET_TO _area (varchar(200)) = @Area()
    -> Dissolver_2
    -> GeometryExtractor
GeometryExtractor
    ATTR = _geometry
    KIND = fmebinary
    REMOVE_GEOMETRY = No
    KIND_LONG = FME Binary
    -> CenterPointReplacer_2
CenterPointReplacer_2
    POINTTYPE = CENTER
    POINT -> PointOnAreaOverlayer_5 [POINT]
Dissolver_2
    ACCUM_INPUT_ATTRS = Drop Incoming Attributes
    CLEANING_TOLERANCE_LOOKUP = AUTO
    CONNECT_Z_MODE_LOOKUP = FIRST_WINS
    DEAGGREGATE_INPUT = Yes
    SUM = _area _overlaps_areas
    CLEANING_TOLERANCE = Automatic
    CONNECT_Z_MODE = First Wins
    AREA -> Counter_2
Counter_2
    CNT_ATTR = _id_area_sobreposicao
    DOMAIN = counter
    SCOPE = Global
    START = 1
    -> AttributeManager_4
AttributeManager_4
    ATTR_TABLE:
      RENAME_SET_VALUE _area > _area_total (varchar(200))
      RENAME_SET_VALUE _overlaps_areas > _overlaps_areas_total (uint32)
    -> PointOnAreaOverlayer_5 [AREA]
    -> Area_Sobreposicao_2
PointOnAreaOverlayer_5
    ATTR_ACCUM_MODE = Merge Incoming
    ATTR_CONFLICT_RES_LOOKUP = ORIGINAL_IF_CONFLICT
    DEAGGREGATE_INPUT = Yes
    OV_ATTR = _overlaps_dissolver
    POLYS_FIRST = NO
    ATTR_CONFLICT_RES = Use Original
    POINT -> Tester_3
Tester_3
    BOOL_OP = OR
    TEST_CLAUSE = TEST @Value(_overlaps_dissolver) > 0
    TEST_MODE = TEST
    PASSED -> AttributeKeeper_3
AttributeKeeper_3
    CREATE_BULK_MODE_FEATURES = NO
    KEEP_ATTRS = _area,_area_total,_id_area_sobreposicao,_overlaps_areas,_overlaps_areas_total
    -> pt_Area_sobrep_2
    -> PointOnAreaOverlayer_6 [POINT]
PointOnAreaOverlayer_6
    ATTR_ACCUM_MODE = Merge Incoming
    ATTR_CONFLICT_RES_LOOKUP = ORIGINAL_IF_CONFLICT
    CANDIDATE_LIST_ATTRS_TO_INCLUDE_MODE_LU = ALL
    CANDIDATE_LIST_NAME = points_dissolver
    DEAGGREGATE_INPUT = Yes
    OV_ATTR = _overlaps_edf_rot
    POLYS_FIRST = NO
    ATTR_CONFLICT_RES = Use Original
    CANDIDATE_LIST_ATTRS_TO_INCLUDE_MODE = All Attributes
    AREA -> PythonCaller_2
PythonCaller_2
    NEW_ATTRIBUTES = s_area int32 s_t_area real32 overlaps_areas real32 overlaps_areas_totais real32 id_area_dissolver char(200) qtd_area_dissolver int32
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              s_area = 0
              s_t_area = [0]
              id_area = []
              overlaps_areas = [0]
              overlaps_areas_totais = [0]

              for i in range(feature.getAttribute('_overlaps_edf_rot')):
                  """
                  print(i,
                      '_area', feature.getAttribute('points_dissolver{'+str(i)+'}._area'),
                      '_area_total', feature.getAttribute('points_dissolver{'+str(i)+'}._area_total'),
                      '_overlaps_areas', feature.getAttribute('points_dissolver{'+str(i)+'}._overlaps_areas'),
                      '_overlaps_areas_total', feature.getAttribute('points_dissolver{'+str(i)+'}._overlaps_areas_total'),
                      '_id_area_sobreposicao', feature.getAttribute('points_dissolver{'+str(i)+'}._id_area_sobreposicao')
                  )
                  """

                  s_area += feature.getAttribute('points_dissolver{'+str(i)+'}._area')
                  if not feature.getAttribute('points_dissolver{'+str(i)+'}._area_total') in s_t_area:
                      s_t_area.append(feature.getAttribute('points_dissolver{'+str(i)+'}._area_total'))
                  if not feature.getAttribute('points_dissolver{'+str(i)+'}._area_total') in overlaps_areas:
                      overlaps_areas.append(feature.getAttribute('points_dissolver{'+str(i)+'}._overlaps_areas'))
                  if not feature.getAttribute('points_dissolver{'+str(i)+'}._overlaps_areas_total') in overlaps_areas_totais:
                      overlaps_areas_totais.append(feature.getAttribute('points_dissolver{'+str(i)+'}._overlaps_areas_total'))
                  if not str(feature.getAttribute('points_dissolver{'+str(i)+'}._id_area_sobreposicao')) in id_area:
                      id_area.append(str(feature.getAttribute('points_dissolver{'+str(i)+'}._id_area_sobreposicao')))

              feature.setAttribute("s_area", s_area)
              feature.setAttribute("s_t_area", sum(s_t_area))
              feature.setAttribute("overlaps_areas", sum(overlaps_areas))
              feature.setAttribute("overlaps_areas_totais", sum(overlaps_areas_totais))
              feature.setAttribute("id_area_dissolver", ','.join(id_area))
              feature.setAttribute("qtd_area_dissolver", len(id_area))

              self.pyoutput(feature)


          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> AttributeKeeper_5
    -> GeometryExtractor_4
GeometryExtractor_4
    ATTR = _geometry
    KIND = fmebinary
    REMOVE_GEOMETRY = No
    KIND_LONG = FME Binary
    -> CenterPointReplacer_6
CenterPointReplacer_6
    POINTTYPE = CENTER
    POINT -> PointOnAreaOverlayer_7 [POINT]
AttributeKeeper_5
    CREATE_BULK_MODE_FEATURES = NO
    KEEP_ATTRS = id_area_dissolver,overlaps_areas,overlaps_areas_totais,s_area,s_t_area
    -> Dissolver_5
Dissolver_5
    ACCUM_INPUT_ATTRS = Drop Incoming Attributes
    CLEANING_TOLERANCE_LOOKUP = AUTO
    CONNECT_Z_MODE_LOOKUP = FIRST_WINS
    DEAGGREGATE_INPUT = Yes
    DIS_ATTR = _qtd_area_sobreposicao_ilha
    SUM = overlaps_areas overlaps_areas_totais s_area s_t_area id_area_dissolver
    CLEANING_TOLERANCE = Automatic
    CONNECT_Z_MODE = First Wins
    AREA -> AttributeManager_5
AttributeManager_5
    ATTR_TABLE:
      RENAME_SET_VALUE s_area > s_area_ilha (int32)
      RENAME_SET_VALUE s_t_area > s_t_area_ilha (real32)
      RENAME_SET_VALUE overlaps_areas > overlaps_areas_ilha (real32)
      RENAME_SET_VALUE overlaps_areas_totais > overlaps_areas_totais_ilha (real32)
      RENAME_SET_VALUE id_area_dissolver > id_area_dissolver_ilha (char(200))
    -> Counter_5
Counter_5
    CNT_ATTR = _ilha_id
    DOMAIN = counter
    SCOPE = Global
    START = 1
    -> PointOnAreaOverlayer_7 [AREA]
    -> Ilhas_2
PointOnAreaOverlayer_7
    ATTR_ACCUM_MODE = Merge Incoming
    ATTR_CONFLICT_RES_LOOKUP = ORIGINAL_IF_CONFLICT
    DEAGGREGATE_INPUT = Yes
    OV_ATTR = _overlaps_ilhas
    POLYS_FIRST = NO
    ATTR_CONFLICT_RES = Use Original
    POINT -> GeometryReplacer_3
GeometryReplacer_3
    KIND = fmebinary
    REMOVE_ATTRIBUTE = Yes
    SOURCE = @Value(_geometry)
    KIND_LONG = FME Binary
    -> Tester_4
Tester_4
    BOOL_OP = OR
    TEST_CLAUSE = TEST @Value(s_area) = 0
    TEST_MODE = TEST
    PASSED -> AttributeCreator_3
    FAILED -> Sorter_2
Sorter_2
    GROUP_BY = _ilha_id
    SORT_PARM = _ilha_id NUMERIC ASCENDING s_area NUMERIC DESCENDING
    SORTED -> ModuloCounter_2
ModuloCounter_2
    CNT_ATTR = _prioridade_visivel
    DOMAIN = @Value(_ilha_id)
    MOD = 9999
    -> AttributeCreator_3
AttributeCreator_3
    ATTR_TABLE = SET_TO _visivel (varchar(200)) = FME_CONDITIONAL:DEFAULT_VALUE'_FME_NO_OP_'BOOL_OP;OR;COMPOSITE_TEST;1;TEST @Value(s_area) = 0'1'BOOL_OP;AND;COMPOSITE_TEST;1 AND 2;TEST @Value(_prioridade_visivel) = 0;TEST @Value(_qtd_area_sobreposicao_ilha) > 1'0'BOOL_OP;AND;COMPOSITE_TEST;1 AND 2 AND 3;TEST @Value(_prioridade_visivel) = 0;TEST @Value(_qtd_area_sobreposicao_ilha) = 1;TEST @Value(s_area) > 100'2'BOOL_OP;AND;COMPOSITE_TEST;1 AND 2 AND 3;TEST @Value(_prioridade_visivel) = 0;TEST @Value(_qtd_area_sobreposicao_ilha) = 1;TEST @Value(s_area) <= 100'3'FME_NUM_CONDITIONS5___
    -> AttributeKeeper_6
    -> Aggregator_2
    -> Aggregator_3
AttributeKeeper_6
    CREATE_BULK_MODE_FEATURES = NO
    KEEP_ATTRS = _visivel,_geometry_original,_largura_edif,_x_original,_y_original,fme_feature_type,id,rotacao,_loop
    -> CenterPointReplacer
CenterPointReplacer
    POINTTYPE = CENTER
    POINT -> FeatureMerger_3 [REQUESTOR]
Aggregator_2
    ACCUM_ATTRS_NAME = Drop Incoming Attributes
    AGGREGATE_TYPE = Homogeneous Collection (If Possible)
    COUNT_ATTR = _qtd_elementos_agreg
    GROUP_BY = fme_feature_type
    MODE = Geometry - Assemble One Level
    SEP = ,
    AGGREGATE -> FeatureMerger_4 [REQUESTOR]
Aggregator_3
    ACCUM_ATTRS_NAME = Drop Incoming Attributes
    AGGREGATE_TYPE = Homogeneous Collection (If Possible)
    COUNT_ATTR = _qtd_elementos_agreg_visivel
    GROUP_BY = _visivel fme_feature_type
    MODE = Geometry - Assemble One Level
    SEP = ,
    AGGREGATE -> Tester
Tester
    BOOL_OP = OR
    TEST_CLAUSE = TEST _visivel NOT_ATTRIBUTE_HAS_A_VALUE ""
    TEST_MODE = TEST
    PASSED -> FeatureMerger_4 [SUPPLIER]
FeatureMerger_4
    ATTR_ACCUM_MODE = Merge Supplier
    ATTR_CONFLICT_RES_LOOKUP = REQUESTOR_IF_CONFLICT
    IGNORE_NULLS = No
    JOIN_KEYS = @Value(fme_feature_type) @Value(fme_feature_type) AUTO
    MERGE_TYPE = Attributes Only
    PROCESS_DUPS = NO
    REJECT_NULL_MISSING_KEYS = No
    SUPPLIERS_FIRST = No
    ATTR_CONFLICT_RES = Use Requestor
    MERGED -> AttributeCreator_5
AttributeCreator_5
    ATTR_TABLE = SET_TO _loop (uint8) = 1
    -> AttributeKeeper_7
AttributeKeeper_7
    CREATE_BULK_MODE_FEATURES = NO
    KEEP_ATTRS = _loop,_qtd_elementos_agreg,_qtd_elementos_agreg_visivel
    -> FeatureMerger_3 [SUPPLIER]
FeatureMerger_3
    ATTR_ACCUM_MODE = Merge Supplier
    ATTR_CONFLICT_RES_LOOKUP = SUPPLIER_IF_CONFLICT
    IGNORE_NULLS = No
    JOIN_KEYS = @Value(_loop) @Value(_loop) AUTO
    MERGE_TYPE = Attributes Only
    PROCESS_DUPS = NO
    REJECT_NULL_MISSING_KEYS = No
    SUPPLIERS_FIRST = No
    ATTR_CONFLICT_RES = Use Supplier
    MERGED -> AttributeCreator_7
    UNMERGED_REQUESTOR -> AttributeCreator_6
AttributeCreator_7
    ATTR_TABLE = SET_TO _attr_miss (uint8) = 1
    -> FeatureMerger_5 [REQUESTOR]
    -> Output_2 (output)
AttributeCreator_6
    ATTR_TABLE = SET_TO _attr_miss (uint8) = 0
    -> FeatureMerger_5 [SUPPLIER]
    -> Output_2 (output)
Output_2 (output)
FeatureMerger_5
    ATTR_ACCUM_MODE = Merge Supplier
    ATTR_CONFLICT_RES_LOOKUP = SUPPLIER_IF_CONFLICT
    IGNORE_NULLS = No
    JOIN_KEYS = @Value(_loop) @Value(_loop) AUTO
    MERGE_TYPE = Attributes Only
    PROCESS_DUPS = NO
    REJECT_NULL_MISSING_KEYS = No
    SUPPLIERS_FIRST = No
    ATTR_CONFLICT_RES = Use Supplier
    MERGED -> Tester_6
    UNMERGED_REQUESTOR -> Tester_6
Tester_6
    BOOL_OP = COMPOSITE
    COMPOSITE_TEST = 1 OR ( 2 AND 3 AND 4 ) OR ( 5 )
    TEST_CLAUSE:
      TEST @Value(_qtd_elementos_agreg) = @Value(_qtd_elementos_agreg_visivel)
      TEST _qtd_elementos_agreg ATTRIBUTE_IS_MISSING ""
      TEST _qtd_elementos_agreg_visivel ATTRIBUTE_IS_MISSING ""
      TEST _visivel ATTRIBUTE_HAS_A_VALUE ""
      TEST @Value(_attr_miss) = 0
    TEST_MODE = TEST
    PASSED -> GeometryFilter_3
    FAILED -> saida (output)
GeometryFilter_3
    FILTER_MODE = SIMPLE
    FILTER_MULTI = FILTER_TYPES]Point]FME_CONTROLLER_QUERY_FILE]]FME_CONTROLLER_CHOICE]Simple
    Point -> AttributeKeeper
AttributeKeeper
    CREATE_BULK_MODE_FEATURES = NO
    KEEP_ATTRS = _largura_edif,_visivel,_x_original,_y_original,fme_feature_type,id,rotacao,_geometry_original
    -> Output (output)
Output (output)
saida (output)
Ilhas_2: Inspector [off]
pt_Area_sobrep_2: Inspector [off]
Area_Sobreposicao_2: Inspector [off]

FME custom transformer Configurar_Visibilidade_Edificacoes
Loop

Edificacoes (input)
    -> Junction_17
Junction_17
    -> Tester_15
Tester_15
    BOOL_OP = OR
    TEST_CLAUSE = TEST _visivel ATTRIBUTE_HAS_A_VALUE ""
    TEST_MODE = TEST
    PASSED -> Visivel_Edif_set
    FAILED -> AttributeKeeper_14
    FAILED -> AttributeKeeper_15
AttributeKeeper_15
    CREATE_BULK_MODE_FEATURES = NO
    KEEP_ATTRS = _largura_edif,_x_original,_y_original,fme_feature_type,id,rotacao,_visivel
    -> PointOnAreaOverlayer_3 [AREA]
Visivel_Edif_set: Inspector
Linhas_Buffers (input)
    -> Junction_18
Junction_18
    -> AttributeKeeper_14
    -> Junction_18_Output
AttributeKeeper_14
    CREATE_BULK_MODE_FEATURES = NO
    KEEP_ATTRS = fme_feature_type,id
    -> AreaOnAreaOverlayer [AREA]
AreaOnAreaOverlayer
    ACCUM_ATTRS_NAME = Drop Incoming Attributes
    CLEANING_TOLERANCE_LOOKUP = 0
    CONNECT_Z_MODE_LOOKUP = FIRST_WINS
    DEAGGREGATE_INPUT = Yes
    OVC_ATTR = _overlaps_areas
    CLEANING_TOLERANCE = 0
    CONNECT_Z_MODE = First Wins
    AREA -> Tester_11
Tester_11
    BOOL_OP = OR
    TEST_CLAUSE = TEST @Value(_overlaps_areas) > 1
    TEST_MODE = TEST
    PASSED -> AttributeCreator_14
AttributeCreator_14
    ATTR_TABLE = SET_TO _area (varchar(200)) = @Area()
    -> Dissolver_3
    -> GeometryExtractor
GeometryExtractor
    ATTR = _geometry
    KIND = fmebinary
    REMOVE_GEOMETRY = No
    KIND_LONG = FME Binary
    -> CenterPointReplacer_2
CenterPointReplacer_2
    POINTTYPE = CENTER
    POINT -> PointOnAreaOverlayer_2 [POINT]
Dissolver_3
    ACCUM_INPUT_ATTRS = Drop Incoming Attributes
    CLEANING_TOLERANCE_LOOKUP = AUTO
    CONNECT_Z_MODE_LOOKUP = FIRST_WINS
    DEAGGREGATE_INPUT = Yes
    SUM = _area _overlaps_areas
    CLEANING_TOLERANCE = Automatic
    CONNECT_Z_MODE = First Wins
    AREA -> Counter_3
Counter_3
    CNT_ATTR = _id_area_sobreposicao
    DOMAIN = counter
    SCOPE = Global
    START = 1
    -> AttributeManager_2
AttributeManager_2
    ATTR_TABLE:
      RENAME_SET_VALUE _area > _area_total (varchar(200))
      RENAME_SET_VALUE _overlaps_areas > _overlaps_areas_total (uint32)
    -> PointOnAreaOverlayer_2 [AREA]
    -> Area_Sobreposicao
PointOnAreaOverlayer_2
    ATTR_ACCUM_MODE = Merge Incoming
    ATTR_CONFLICT_RES_LOOKUP = ORIGINAL_IF_CONFLICT
    DEAGGREGATE_INPUT = Yes
    OV_ATTR = _overlaps_dissolver
    POLYS_FIRST = NO
    ATTR_CONFLICT_RES = Use Original
    POINT -> Tester_12
Tester_12
    BOOL_OP = OR
    TEST_CLAUSE = TEST @Value(_overlaps_dissolver) > 0
    TEST_MODE = TEST
    PASSED -> AttributeKeeper_13
AttributeKeeper_13
    CREATE_BULK_MODE_FEATURES = NO
    KEEP_ATTRS = _area,_area_total,_id_area_sobreposicao,_overlaps_areas,_overlaps_areas_total
    -> pt_Area_sobrep
    -> PointOnAreaOverlayer_3 [POINT]
PointOnAreaOverlayer_3
    ATTR_ACCUM_MODE = Merge Incoming
    ATTR_CONFLICT_RES_LOOKUP = ORIGINAL_IF_CONFLICT
    CANDIDATE_LIST_ATTRS_TO_INCLUDE_MODE_LU = ALL
    CANDIDATE_LIST_NAME = points_dissolver
    DEAGGREGATE_INPUT = Yes
    OV_ATTR = _overlaps_edf_rot
    POLYS_FIRST = NO
    ATTR_CONFLICT_RES = Use Original
    CANDIDATE_LIST_ATTRS_TO_INCLUDE_MODE = All Attributes
    AREA -> PythonCaller_3
PythonCaller_3
    NEW_ATTRIBUTES = s_area int32 s_t_area real32 overlaps_areas real32 overlaps_areas_totais real32 id_area_dissolver char(200) qtd_area_dissolver int32
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              s_area = 0
              s_t_area = [0]
              id_area = []
              overlaps_areas = [0]
              overlaps_areas_totais = [0]

              for i in range(feature.getAttribute('_overlaps_edf_rot')):
                  """
                  print(i,
                      '_area', feature.getAttribute('points_dissolver{'+str(i)+'}._area'),
                      '_area_total', feature.getAttribute('points_dissolver{'+str(i)+'}._area_total'),
                      '_overlaps_areas', feature.getAttribute('points_dissolver{'+str(i)+'}._overlaps_areas'),
                      '_overlaps_areas_total', feature.getAttribute('points_dissolver{'+str(i)+'}._overlaps_areas_total'),
                      '_id_area_sobreposicao', feature.getAttribute('points_dissolver{'+str(i)+'}._id_area_sobreposicao')
                  )
                  """

                  s_area += feature.getAttribute('points_dissolver{'+str(i)+'}._area')
                  if not feature.getAttribute('points_dissolver{'+str(i)+'}._area_total') in s_t_area:
                      s_t_area.append(feature.getAttribute('points_dissolver{'+str(i)+'}._area_total'))
                  if not feature.getAttribute('points_dissolver{'+str(i)+'}._area_total') in overlaps_areas:
                      overlaps_areas.append(feature.getAttribute('points_dissolver{'+str(i)+'}._overlaps_areas'))
                  if not feature.getAttribute('points_dissolver{'+str(i)+'}._overlaps_areas_total') in overlaps_areas_totais:
                      overlaps_areas_totais.append(feature.getAttribute('points_dissolver{'+str(i)+'}._overlaps_areas_total'))
                  if not str(feature.getAttribute('points_dissolver{'+str(i)+'}._id_area_sobreposicao')) in id_area:
                      id_area.append(str(feature.getAttribute('points_dissolver{'+str(i)+'}._id_area_sobreposicao')))

              feature.setAttribute("s_area", s_area)
              feature.setAttribute("s_t_area", sum(s_t_area))
              feature.setAttribute("overlaps_areas", sum(overlaps_areas))
              feature.setAttribute("overlaps_areas_totais", sum(overlaps_areas_totais))
              feature.setAttribute("id_area_dissolver", ','.join(id_area))
              feature.setAttribute("qtd_area_dissolver", len(id_area))

              self.pyoutput(feature)


          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> AttributeKeeper_16
    -> GeometryExtractor_2
GeometryExtractor_2
    ATTR = _geometry
    KIND = fmebinary
    REMOVE_GEOMETRY = No
    KIND_LONG = FME Binary
    -> CenterPointReplacer_3
CenterPointReplacer_3
    POINTTYPE = CENTER
    POINT -> PointOnAreaOverlayer_4 [POINT]
AttributeKeeper_16
    CREATE_BULK_MODE_FEATURES = NO
    KEEP_ATTRS = id_area_dissolver,overlaps_areas,overlaps_areas_totais,s_area,s_t_area
    -> Dissolver_4
Dissolver_4
    ACCUM_INPUT_ATTRS = Drop Incoming Attributes
    CLEANING_TOLERANCE_LOOKUP = AUTO
    CONNECT_Z_MODE_LOOKUP = FIRST_WINS
    DEAGGREGATE_INPUT = Yes
    DIS_ATTR = _qtd_area_sobreposicao_ilha
    SUM = overlaps_areas overlaps_areas_totais s_area s_t_area id_area_dissolver
    CLEANING_TOLERANCE = Automatic
    CONNECT_Z_MODE = First Wins
    AREA -> AttributeManager_3
AttributeManager_3
    ATTR_TABLE:
      RENAME_SET_VALUE s_area > s_area_ilha (int32)
      RENAME_SET_VALUE s_t_area > s_t_area_ilha (real32)
      RENAME_SET_VALUE overlaps_areas > overlaps_areas_ilha (real32)
      RENAME_SET_VALUE overlaps_areas_totais > overlaps_areas_totais_ilha (real32)
      RENAME_SET_VALUE id_area_dissolver > id_area_dissolver_ilha (char(200))
    -> Counter_4
Counter_4
    CNT_ATTR = _ilha_id
    DOMAIN = counter
    SCOPE = Global
    START = 1
    -> PointOnAreaOverlayer_4 [AREA]
    -> Ilhas
PointOnAreaOverlayer_4
    ATTR_ACCUM_MODE = Merge Incoming
    ATTR_CONFLICT_RES_LOOKUP = ORIGINAL_IF_CONFLICT
    DEAGGREGATE_INPUT = Yes
    OV_ATTR = _overlaps_ilhas
    POLYS_FIRST = NO
    ATTR_CONFLICT_RES = Use Original
    POINT -> GeometryReplacer_2
GeometryReplacer_2
    KIND = fmebinary
    REMOVE_ATTRIBUTE = Yes
    SOURCE = @Value(_geometry)
    KIND_LONG = FME Binary
    -> Tester_13
Tester_13
    BOOL_OP = OR
    TEST_CLAUSE = TEST @Value(s_area) = 0
    TEST_MODE = TEST
    PASSED -> AttributeCreator_18
    FAILED -> Sorter_3
Sorter_3
    GROUP_BY = _ilha_id
    SORT_PARM = _ilha_id NUMERIC ASCENDING s_area NUMERIC DESCENDING
    SORTED -> ModuloCounter_3
ModuloCounter_3
    CNT_ATTR = _prioridade_visivel
    DOMAIN = @Value(_ilha_id)
    MOD = 9999
    -> AttributeCreator_18
AttributeCreator_18
    ATTR_TABLE = SET_TO _visivel (varchar(200)) = FME_CONDITIONAL:DEFAULT_VALUE'_FME_NO_OP_'BOOL_OP;OR;COMPOSITE_TEST;1;TEST @Value(s_area) = 0'1'BOOL_OP;AND;COMPOSITE_TEST;1 AND 2;TEST @Value(_prioridade_visivel) = 0;TEST @Value(_qtd_area_sobreposicao_ilha) > 1'0'BOOL_OP;AND;COMPOSITE_TEST;1 AND 2 AND 3;TEST @Value(_prioridade_visivel) = 0;TEST @Value(_qtd_area_sobreposicao_ilha) = 1;TEST @Value(s_area) > 100'2'BOOL_OP;AND;COMPOSITE_TEST;1 AND 2 AND 3;TEST @Value(_prioridade_visivel) = 0;TEST @Value(_qtd_area_sobreposicao_ilha) = 1;TEST @Value(s_area) <= 100'3'FME_NUM_CONDITIONS5___
    -> AttributeKeeper_20
AttributeKeeper_20
    CREATE_BULK_MODE_FEATURES = NO
    KEEP_ATTRS = _visivel,fme_feature_type,id,rotacao,_x_original,_y_original,_largura_edif
    -> Edificacaos_Visualizacao
Edificacaos_Visualizacao: Inspector
    TACKATTRS = _visivel
Ilhas: Inspector
pt_Area_sobrep: Inspector
Area_Sobreposicao: Inspector
Junction_18_Output: Inspector
Edificacoes (output)

FME custom transformer Agregar_elementos_box

Parameters:
- FME_FEATURE_TYPE = @Value(fme_feature_type)   # Fme Feature Type
- ID = @Value(id)   # id

Elementos (input)
    -> GeometryFilter_2
GeometryFilter_2
    FILTER_MODE = SIMPLE
    FILTER_MULTI = FILTER_TYPES]"Point Line"]FME_CONTROLLER_QUERY_FILE]]FME_CONTROLLER_CHOICE]Simple
    Point -> PointOnAreaOverlayer_3 [POINT]
    Curve -> LineOnAreaOverlayer_3 [LINE]
Area (input)
    -> Junction_6
Junction_6
    -> PointOnAreaOverlayer_3 [AREA]
    -> LineOnAreaOverlayer_3 [AREA]
PointOnAreaOverlayer_3
    ATTR_ACCUM_MODE = Prefic Incoming
    DEAGGREGATE_INPUT = Yes
    INCOMING_PREFIX = GRID_
    OV_ATTR = _overlaps_grid
    POLYS_FIRST = NO
    POINT -> Tester_5
LineOnAreaOverlayer_3
    ATTR_ACCUM_MODE = Prefix Incoming
    CLEANING_TOLERANCE_LOOKUP = AUTO
    DEAGGREGATE_INPUT = Yes
    INCOMING_PREFIX = GRID_
    OVERLAY_TYPE = LINE_ON_AREA
    OV_ATTR = _overlaps_grid
    CLEANING_TOLERANCE = Automatic
    LINE -> Tester_5
Tester_5
    BOOL_OP = OR
    TEST_CLAUSE = TEST @Value(_overlaps_grid) > 0
    TEST_MODE = TEST
    PASSED -> Output (output)
Output (output)

FME custom transformer Definir_Tamanho_Txt_Linhas

Parameters:
- NOME = @Value(nome)   # nome
- ID = @Value(id)   # id

Feature_Entrada (input)
    -> Tester_3
Tester_3
    BOOL_OP = AND
    TEST_CLAUSE:
      TEST nome ATTRIBUTE_HAS_A_VALUE ""
      TEST @StringLength(@Value(nome)) >= 3
    TEST_MODE = TEST
    PASSED -> LineCombiner
    PASSED -> CoordinateExtractor
    PASSED -> FeatureMerger_2 [REQUESTOR]
LineCombiner
    ACCUM_ATTRS_NAME = Use Attributes From One Feature
    BREAK_CONNECTION_ATTRIBUTES = nome
    CLOSE = yes
    CONNECT_Z_MODE_LOOKUP = FIRST_WINS
    CONSIDER_NODE_ELEVATION_LOOKUP = NO
    DEAGGREGATE_GEOMETRY = Deaggregate
    JUNCTIONS_IGNORE_ATTRIBUTES = No
    LINES_AS_SEGMENTS = No
    NODED = VERTEX_NODED
    PRESERVE = no
    BREAK = no
    CONNECT_Z_MODE = First Wins
    CONSIDER_NODE_ELEVATION = no
    TOPOLOGY = Vertex Noded
    LINE -> AttributeKeeper_5
AttributeKeeper_5
    CREATE_BULK_MODE_FEATURES = NO
    KEEP_ATTRS = nome
    -> AttributeCreator_6
AttributeCreator_6
    ATTR_TABLE:
      SET_TO _comprimento (varchar(200)) = @Length()
      SET_TO tamanho_txt (varchar(200)) = FME_CONDITIONAL:DEFAULT_VALUE'_FME_NO_OP_'BOOL_OP;OR;COMPOSITE_TEST;1;TEST @Value(_comprimento) > 1000'12'BOOL_OP;OR;COMPOSITE_TEST;1;TEST @Value(_comprimento) > 500'10'FME_NUM_CONDITIONS3___
    -> Bufferer_3
Bufferer_3
    ANGLE = 22.5
    CAP_STYLE_LOOKUP = CAP_ARC
    CORNER_STYLE_LOOKUP = JOIN_ARC
    MODE = AREA
    OFFSET = 5
    OFFSET_UNITS = METERS
    PRECISION = APPROX
    CAP_STYLE = Arc
    CORNER_STYLE = Arc
    BUFFERED -> PointOnAreaOverlayer [AREA]
CoordinateExtractor
    IND = 0
    RECURSIVE = No
    X_ATTR = _x_ini
    Y_ATTR = _y_ini
    MODE = Specify Coordinate
    -> VertexCounter
VertexCounter
    CNT_ATTR = _vertexcount
    -> CoordinateExtractor_2
CoordinateExtractor_2
    IND = @Value(_vertexcount) - 1
    RECURSIVE = No
    X_ATTR = _x_fin
    Y_ATTR = _y_fin
    MODE = Specify Coordinate
    -> AttributeKeeper_6
AttributeKeeper_6
    CREATE_BULK_MODE_FEATURES = NO
    KEEP_ATTRS = _vertexcount,_x_ini,_y_ini,nome,_x_fin,_y_fin,id
    -> VertexCreator
    -> VertexCreator_2
VertexCreator
    MEASURE_TYPE_LOOKUP = CONTINUOUS
    MODE = REPLACE
    XVAL = @Value(_x_ini)
    YVAL = @Value(_y_ini)
    MEASURE_TYPE = Continuous
    MODE_NAME = Replace with Point
    -> PointOnAreaOverlayer [POINT]
VertexCreator_2
    MEASURE_TYPE_LOOKUP = CONTINUOUS
    MODE = REPLACE
    XVAL = @Value(_x_fin)
    YVAL = @Value(_y_fin)
    MEASURE_TYPE = Continuous
    MODE_NAME = Replace with Point
    -> PointOnAreaOverlayer [POINT]
PointOnAreaOverlayer
    ATTR_ACCUM_MODE = Merge Incoming
    ATTR_CONFLICT_RES_LOOKUP = ORIGINAL_IF_CONFLICT
    DEAGGREGATE_INPUT = Yes
    OV_ATTR = _overlaps
    POLYS_FIRST = NO
    ATTR_CONFLICT_RES = Use Original
    POINT -> Tester_4
Tester_4
    BOOL_OP = OR
    TEST_CLAUSE = TEST @Value(_overlaps) > 0
    TEST_MODE = TEST
    PASSED -> Aggregator_2
Aggregator_2
    ACCUM_ATTRS_NAME = Merge Incoming Attributes
    AGGREGATE_TYPE = Homogeneous Collection (If Possible)
    COUNT_ATTR = _count_agreg
    GROUP_BY = id nome
    MODE = Geometry - Assemble One Level
    SEP = ,
    AGGREGATE -> Tester_5
Tester_5
    BOOL_OP = OR
    TEST_CLAUSE = TEST @Value(_count_agreg) > 1
    TEST_MODE = TEST
    PASSED -> FeatureMerger_2 [SUPPLIER]
FeatureMerger_2
    ATTR_ACCUM_MODE = Merge Supplier
    ATTR_CONFLICT_RES_LOOKUP = SUPPLIER_IF_CONFLICT
    IGNORE_NULLS = No
    JOIN_KEYS = @Value(id) @Value(id) AUTO @Value(nome) @Value(nome) AUTO
    MERGE_TYPE = Attributes Only
    PROCESS_DUPS = NO
    REJECT_NULL_MISSING_KEYS = No
    SUPPLIERS_FIRST = No
    ATTR_CONFLICT_RES = Use Supplier
    MERGED -> Feature_Saida (output)
Feature_Saida (output)

FME custom transformer Box_edficacao_rotacionado

Parameters:
- _Y_ORIGINAL = @Value(_y_original)   # Y Original
- _LARGURA_EDIF = @Value(_largura_edif)   # Largura Edif
- ROTACAO = @Value(rotacao)   # rotacao
- _X_ORIGINAL = @Value(_x_original)   # X Original

Bufferer_7_Input (input)
    -> Bufferer_7
Bufferer_7
    ANGLE = 22.5
    CAP_STYLE_LOOKUP = CAP_PROJECTING
    CORNER_STYLE_LOOKUP = JOIN_MITER
    MITER_LIMIT = 1
    MODE = AREA
    OFFSET = @Value(_largura_edif)
    OFFSET_UNITS = METERS
    PRECISION = APPROX
    CAP_STYLE = Square
    CORNER_STYLE = Miter
    BUFFERED -> Rotator_2
Rotator_2
    ANGLE = @Value(rotacao)
    XORIG = @Value(_x_original)
    YORIG = @Value(_y_original)
    ROTATED -> Rotator_2_Rotated (output)
Rotator_2_Rotated (output)

FME custom transformer teste_loop_displace_edif

Parameters:
- ID = @Value(id)   # id
- _MOVIDO = @Value(_movido)   # Movido
- _GEOMETRY_ORIGINAL = @Value(_geometry_original)   # Geometry Original
- _LARGURA_EDIF = @Value(_largura_edif)   # Largura Edif
- _VISIVEL = @Value(_visivel)   # Visivel
- _X_ORIGINAL = @Value(_x_original)   # X Original
- _Y_ORIGINAL = @Value(_y_original)   # Y Original
- FME_FEATURE_TYPE = @Value(fme_feature_type)   # Fme Feature Type
- ROTACAO = @Value(rotacao)   # rotacao

VariableSetter_Input (input)
    -> VariableSetter
VariableSetter
    SCOPE = Global
    VALUE = 1
    VARNAME = _attribute_miss
    -> AttributeCreator_30
AttributeCreator_30
    ATTR_TABLE = SET_TO _loop (uint8) = 1
    -> GeometryFilter
GeometryFilter
    FILTER_MODE = SIMPLE
    FILTER_MULTI = FILTER_TYPES]"Point Area"]FME_CONTROLLER_QUERY_FILE]]FME_CONTROLLER_CHOICE]Simple
    Point -> Tester_14
    Area -> Junction_20
    Area -> Output_2 (output) [off]
Junction_20
    -> AreaOnAreaOverlayer [AREA]
    -> Displacer [BASE]
Tester_14
    BOOL_OP = OR
    TEST_CLAUSE = TEST _visivel NOT_ATTRIBUTE_HAS_A_VALUE ""
    TEST_MODE = TEST
    PASSED -> GeometryReplacer_2
    PASSED -> FeatureMerger_3 [REQUESTOR]
    FAILED -> Junction_24
Junction_24
    -> ALL_edif_movidas
    -> FeatureMerger_5 [REQUESTOR]
GeometryReplacer_2
    KIND = fmebinary
    REMOVE_ATTRIBUTE = No
    SOURCE = @Value(_geometry_original)
    KIND_LONG = FME Binary
    -> CoordinateExtractor_3
CoordinateExtractor_3
    LIST_NAME = _indices
    RECURSIVE = Yes
    MODE = All Coordinates
    -> CenterPointExtractor
CenterPointExtractor
    CENTX = _inside_x
    CENTY = _inside_y
    EXTRACTIONMODE = CENTEROFGRAV
    -> AttributeCreator_14
AttributeCreator_14
    ATTR_TABLE:
      SET_TO _v_x_1 (varchar(200)) = @Value(_indices{1}.x)
      SET_TO _v_x_2 (varchar(200)) = @Value(_indices{2}.x)
      SET_TO _v_x_3 (varchar(200)) = @Value(_indices{3}.x)
      SET_TO _v_x_4 (varchar(200)) = @Value(_indices{4}.x)
      SET_TO _v_y_1 (varchar(200)) = @Value(_indices{1}.y)
      SET_TO _v_y_2 (varchar(200)) = @Value(_indices{2}.y)
      SET_TO _v_y_3 (varchar(200)) = @Value(_indices{3}.y)
      SET_TO _v_y_4 (varchar(200)) = @Value(_indices{4}.y)
    -> AreaOnAreaOverlayer [AREA]
    -> edifi
    -> AttributeKeeper_14
AttributeKeeper_14
    CREATE_BULK_MODE_FEATURES = NO
    KEEP_ATTRS = _inside_x,_inside_y,_largura_edif,_v_x_1,_v_x_2,_v_x_3,_v_x_4,_v_y_1,_v_y_2,_v_y_3,_v_y_4,_x_original,_y_original,fme_feature_type,rotacao,id,_movido,_visivel,_geometry_original,_loop
    -> VertexCreator_6
    -> VertexCreator_5
    -> VertexCreator_8
    -> VertexCreator_7
VertexCreator_5
    MEASURE_TYPE_LOOKUP = CONTINUOUS
    MODE = REPLACE
    XVAL = @Value(_v_x_1)
    YVAL = @Value(_v_y_1)
    MEASURE_TYPE = Continuous
    MODE_NAME = Replace with Point
    -> AttributeCreator_17
AttributeCreator_17
    ATTR_TABLE:
      SET_TO fme_feature_type (char(50)) = vertices_edificacao
      SET_TO nr_vertice (uint8) = 1
    -> Junction_21
VertexCreator_6
    MEASURE_TYPE_LOOKUP = CONTINUOUS
    MODE = REPLACE
    XVAL = @Value(_v_x_2)
    YVAL = @Value(_v_y_2)
    MEASURE_TYPE = Continuous
    MODE_NAME = Replace with Point
    -> AttributeCreator_18
AttributeCreator_18
    ATTR_TABLE:
      SET_TO fme_feature_type (char(50)) = vertices_edificacao
      SET_TO nr_vertice (uint8) = 2
    -> Junction_21
VertexCreator_7
    MEASURE_TYPE_LOOKUP = CONTINUOUS
    MODE = REPLACE
    XVAL = @Value(_v_x_3)
    YVAL = @Value(_v_y_3)
    MEASURE_TYPE = Continuous
    MODE_NAME = Replace with Point
    -> AttributeCreator_19
AttributeCreator_19
    ATTR_TABLE:
      SET_TO fme_feature_type (char(50)) = vertices_edificacao
      SET_TO nr_vertice (uint8) = 3
    -> Junction_21
VertexCreator_8
    MEASURE_TYPE_LOOKUP = CONTINUOUS
    MODE = REPLACE
    XVAL = @Value(_v_x_4)
    YVAL = @Value(_v_y_4)
    MEASURE_TYPE = Continuous
    MODE_NAME = Replace with Point
    -> AttributeCreator_20
AttributeCreator_20
    ATTR_TABLE:
      SET_TO fme_feature_type (char(50)) = vertices_edificacao
      SET_TO nr_vertice (uint8) = 4
    -> Junction_21
Junction_21
    -> vertices
    -> PointOnAreaOverlayer_2 [POINT]
vertices: Inspector [off]
    TACKATTRS = nr_vertice
AreaOnAreaOverlayer
    ACCUM_ATTRS_NAME = Use Attributes From One Feature
    CLEANING_TOLERANCE_LOOKUP = AUTO
    CONNECT_Z_MODE_LOOKUP = FIRST_WINS
    DEAGGREGATE_INPUT = Yes
    LIST_ATTRS_TO_INCLUDE = fme_feature_type id
    LIST_NAME = _over
    OVC_ATTR = _overlaps
    CLEANING_TOLERANCE = Automatic
    CONNECT_Z_MODE = First Wins
    AREA -> PythonCaller_3
PythonCaller_3
    NEW_ATTRIBUTES = overlaps_linhas_buffers int8
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              overlaps = [False, False]

              for i in range(feature.getAttribute('_overlaps')):

                  if(feature.getAttribute('_over{'+str(i)+'}.fme_feature_type') == "constr_edificacao_p"):
                      overlaps[0] = True
                  else:
                      overlaps[1] = True
              overlaps_linhas_buffers = overlaps[0] and overlaps[1] if 1 else 0

              feature.setAttribute("overlaps_linhas_buffers", overlaps_linhas_buffers)
              self.pyoutput(feature)


          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> Tester_11
Tester_11
    BOOL_OP = OR
    TEST_CLAUSE = TEST @Value(overlaps_linhas_buffers) = Yes
    TEST_MODE = TEST
    PASSED -> AttributeCreator_16
    FAILED -> Tester_11_Failed
AttributeCreator_16
    ATTR_TABLE = SET_TO _area_sobreposicao (varchar(200)) = @Area()
    -> AttributeKeeper_13
AttributeKeeper_13
    CREATE_BULK_MODE_FEATURES = NO
    KEEP_ATTRS = _area_sobreposicao
    -> sobreposicao
    -> PointOnAreaOverlayer_2 [AREA]
sobreposicao: Inspector
PointOnAreaOverlayer_2
    ATTR_ACCUM_MODE = Merge Incoming
    ATTR_CONFLICT_RES_LOOKUP = ORIGINAL_IF_CONFLICT
    DEAGGREGATE_INPUT = Yes
    OV_ATTR = _overlaps
    POLYS_FIRST = NO
    ATTR_CONFLICT_RES = Use Original
    POINT -> PointOnAreaOverlayer_2_Point
    POINT -> Tester_12
Tester_12
    BOOL_OP = OR
    TEST_CLAUSE = TEST @Value(_overlaps) > 0
    TEST_MODE = TEST
    PASSED -> CoordinateExtractor_4
CoordinateExtractor_4
    IND = 0
    RECURSIVE = No
    X_ATTR = _x
    Y_ATTR = _y
    MODE = Specify Coordinate
    -> Displacer [CANDIDATE]
Displacer
    DISPLACE_ENDPOINTS = No
    MIN_DISTANCE = 0.1
    MULTI_BASE = YES
    STIFFNESS = 1
    BASE_TYPE = Multiple Bases
    DISPLACED -> Displacer_Displaced
    DISPLACED -> VertexCreator_9
    DISPLACED -> CoordinateExtractor_5
    UNTOUCHED -> Displacer_Untouched
    INVALID_BASE -> Displacer_InvalidBase
    INVALID_CANDIDATE -> Displacer_InvalidCandidate
    EXTRA_BASE -> Displacer_ExtraBase
VertexCreator_9
    ALLOW_DUPLICATES = YES
    CLOSE_LINES = Yes
    MEASURE_TYPE_LOOKUP = CONTINUOUS
    MISSING_VAL_MODE_LOOKUP = COMPUTE_NANS
    MODE = ADD
    XVAL = @Value(_x)
    YVAL = @Value(_y)
    IGNORE_DUPLICATES = No
    MEASURE_TYPE = Continuous
    MISSING_VAL_MODE = Compute
    MODE_NAME = Add Point
    -> desloc_line
desloc_line: Inspector
CoordinateExtractor_5
    IND = 0
    RECURSIVE = No
    X_ATTR = _x_desloc
    Y_ATTR = _y_desloc
    MODE = Specify Coordinate
    -> AttributeCreator_21
AttributeCreator_21
    ATTR_TABLE:
      SET_TO _x_desloc_delta (real64) = @Evaluate(@Value(_x_desloc) - @Value(_x))
      SET_TO _y_desloc_delta (real64) = @Evaluate(@Value(_y_desloc) - @Value(_y))
    -> Aggregator_2
Aggregator_2
    ACCUM_ATTRS_NAME = Drop Incoming Attributes
    AGGREGATE_TYPE = Homogeneous Collection (If Possible)
    COUNT_ATTR = _count_vertice_displace
    GROUP_BY = fme_feature_type id
    LIST_NAME = displace
    MODE = Geometry - Assemble One Level
    SEP = ,
    AGGREGATE -> Aggregator_2_Aggregate
    AGGREGATE -> FeatureMerger_3 [SUPPLIER]
Aggregator_2_Aggregate: Inspector [off]
FeatureMerger_3
    ATTR_ACCUM_MODE = Merge Supplier
    ATTR_CONFLICT_RES_LOOKUP = REQUESTOR_IF_CONFLICT
    IGNORE_NULLS = No
    JOIN_KEYS = @Value(id) @Value(displace{0}.id) AUTO
    MERGE_TYPE = Attributes Only
    PROCESS_DUPS = NO
    REJECT_NULL_MISSING_KEYS = No
    SUPPLIERS_FIRST = No
    ATTR_CONFLICT_RES = Use Requestor
    MERGED -> PythonCaller_2
    UNMERGED_REQUESTOR -> AttributeCreator_24
PythonCaller_2
    NEW_ATTRIBUTES = x_desloc_delta real32 y_desloc_delta real32 nr_vertie int32 area_sobreposicao_vertice real32 x_desloc real32 y_desloc real32 desloc_distancia_final real32 desloc_distancia_inicial real32
    PYTHONSOURCE:
      import fme
      import fmeobjects
      from math import sqrt

      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              x_desloc_delta = None
              y_desloc_delta = None
              nr_vertie = 0
              area_sobreposicao_vertice = 0.0
              x_desloc = None
              y_desloc = None
              x1, y1 = (feature.getAttribute('displace{0}._inside_x'), feature.getAttribute('displace{0}._inside_y'))
              desloc_distancia_inicial = None
              desloc_distancia_final = None

              for i in range(feature.getAttribute('_count_vertice_displace')):

                  x2, y2 = (feature.getAttribute('displace{'+str(i)+'}._x'), feature.getAttribute('displace{'+str(i)+'}._y'))
                  x3, y3 = (feature.getAttribute('displace{'+str(i)+'}._x_desloc'), feature.getAttribute('displace{'+str(i)+'}._y_desloc'))
                  distancia_inicial = sqrt((x2 - x1)**2 + (y2 - y1)**2)
                  distancia_final = sqrt((x3 - x1)**2 + (y3 - y1)**2)

                  if(feature.getAttribute('displace{'+str(i)+'}._area_sobreposicao') > area_sobreposicao_vertice and distancia_final <= distancia_inicial):
                      x_desloc_delta = feature.getAttribute('displace{'+str(i)+'}._x_desloc_delta')
                      y_desloc_delta = feature.getAttribute('displace{'+str(i)+'}._y_desloc_delta')
                      nr_vertie = feature.getAttribute('displace{'+str(i)+'}.nr_vertice')
                      area_sobreposicao_vertice = feature.getAttribute('displace{'+str(i)+'}._area_sobreposicao')
                      x_desloc = feature.getAttribute('displace{'+str(i)+'}._x_desloc')
                      y_desloc = feature.getAttribute('displace{'+str(i)+'}._y_desloc')
                      desloc_distancia_inicial = distancia_inicial
                      desloc_distancia_final = distancia_final

              feature.setAttribute("x_desloc_delta", x_desloc_delta)
              feature.setAttribute("y_desloc_delta", y_desloc_delta)
              feature.setAttribute("nr_vertie", nr_vertie)
              feature.setAttribute("area_sobreposicao_vertice", area_sobreposicao_vertice)
              feature.setAttribute("x_desloc", x_desloc)
              feature.setAttribute("y_desloc", y_desloc)
              feature.setAttribute("desloc_distancia_inicial", desloc_distancia_inicial)
              feature.setAttribute("desloc_distancia_final", desloc_distancia_final)
              self.pyoutput(feature)


          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> PythonCaller_2_Output
    -> Tester_13
PythonCaller_2_Output: Inspector [off]
Tester_13
    BOOL_OP = OR
    TEST_CLAUSE = TEST @Value(nr_vertie) > 0
    TEST_MODE = TEST
    PASSED -> Tester_15
    FAILED -> AttributeCreator_23
Tester_15
    BOOL_OP = OR
    TEST_CLAUSE = TEST @Value(_movido) < 4
    TEST_MODE = TEST
    PASSED -> Offsetter_3
    FAILED -> AttributeCreator_23
Offsetter_3
    MODE_LOOKUP = CARTESIAN
    XOFF = @Value(x_desloc_delta)
    YOFF = @Value(y_desloc_delta)
    ZOFF = 0
    MODE = Cartesian Coordinate
    OFFSET -> CoordinateExtractor
CoordinateExtractor
    IND = 0
    RECURSIVE = No
    X_ATTR = _x_original
    Y_ATTR = _y_original
    Z_DEFAULT = 0
    MODE = Specify Coordinate
    -> AttributeCreator_25
AttributeCreator_25
    ATTR_TABLE = SET_TO _movido (real64) = @Evaluate(@Value(_movido) + 1)
    -> Offsetter_3_Offset
    -> Junction_22
Offsetter_3_Offset: Inspector
AttributeCreator_23
    ATTR_TABLE = SET_TO _visivel (uint8) = 0
    -> Junction_22
AttributeCreator_24
    ATTR_TABLE = SET_TO _visivel (uint8) = 1
    -> Junction_22
Junction_22
    -> ALL_edif_movidas
    -> Aggregator_5
    -> Aggregator_6
    -> FeatureMerger_5 [REQUESTOR]
ALL_edif_movidas: Inspector [off]
Aggregator_5
    ACCUM_ATTRS_NAME = Drop Incoming Attributes
    AGGREGATE_TYPE = Homogeneous Collection (If Possible)
    COUNT_ATTR = _qtd_elementos_agreg
    GROUP_BY = fme_feature_type
    MODE = Geometry - Assemble One Level
    SEP = ,
    AGGREGATE -> FeatureMerger_4 [REQUESTOR]
Aggregator_6
    ACCUM_ATTRS_NAME = Drop Incoming Attributes
    AGGREGATE_TYPE = Homogeneous Collection (If Possible)
    COUNT_ATTR = _qtd_elementos_agreg_visivel
    GROUP_BY = _visivel fme_feature_type
    MODE = Geometry - Assemble One Level
    SEP = ,
    AGGREGATE -> Tester_16
Tester_16
    BOOL_OP = OR
    TEST_CLAUSE = TEST _visivel NOT_ATTRIBUTE_HAS_A_VALUE ""
    TEST_MODE = TEST
    PASSED -> FeatureMerger_4 [SUPPLIER]
FeatureMerger_4
    ATTR_ACCUM_MODE = Merge Supplier
    ATTR_CONFLICT_RES_LOOKUP = REQUESTOR_IF_CONFLICT
    IGNORE_NULLS = No
    JOIN_KEYS = @Value(fme_feature_type) @Value(fme_feature_type) AUTO
    MERGE_TYPE = Attributes Only
    PROCESS_DUPS = NO
    REJECT_NULL_MISSING_KEYS = No
    SUPPLIERS_FIRST = No
    ATTR_CONFLICT_RES = Use Requestor
    MERGED -> AttributeCreator_29
AttributeCreator_29
    ATTR_TABLE = SET_TO _loop (uint8) = 1
    -> AttributeKeeper_17
AttributeKeeper_17
    CREATE_BULK_MODE_FEATURES = NO
    KEEP_ATTRS = _qtd_elementos_agreg,_qtd_elementos_agreg_visivel,fme_feature_type,_loop
    -> FeatureMerger_5 [SUPPLIER]
FeatureMerger_5
    ATTR_ACCUM_MODE = Merge Supplier
    ATTR_CONFLICT_RES_LOOKUP = SUPPLIER_IF_CONFLICT
    IGNORE_NULLS = No
    JOIN_KEYS = @Value(_loop) @Value(_loop) AUTO
    MERGE_TYPE = Attributes Only
    PROCESS_DUPS = NO
    REJECT_NULL_MISSING_KEYS = No
    SUPPLIERS_FIRST = No
    ATTR_CONFLICT_RES = Use Supplier
    MERGED -> AttributeCreator_28
    UNMERGED_REQUESTOR -> VariableSetter_2
AttributeCreator_28
    ATTR_TABLE = SET_TO _attr_miss (uint8) = 1
    -> VariableRetriever
VariableSetter_2
    SCOPE = Global
    VALUE = 0
    VARNAME = _attribute_miss
    -> AttributeCreator_27
AttributeCreator_27
    ATTR_TABLE = SET_TO _attr_miss (uint8) = 0
    -> VariableRetriever
VariableRetriever
    SCOPE = Global
    VALUE_ATTR = _attr_miss
    VARNAME = _attribute_miss
    -> Tester_17
Tester_17
    BOOL_OP = COMPOSITE
    COMPOSITE_TEST = 1 OR ( 2 AND 3 AND 4 ) OR ( 5 )
    TEST_CLAUSE:
      TEST @Value(_qtd_elementos_agreg) = @Value(_qtd_elementos_agreg_visivel)
      TEST _qtd_elementos_agreg ATTRIBUTE_IS_MISSING ""
      TEST _qtd_elementos_agreg_visivel ATTRIBUTE_IS_MISSING ""
      TEST _visivel ATTRIBUTE_HAS_A_VALUE ""
      TEST @Value(_attr_miss) = 0
    TEST_MODE = TEST
    PASSED -> GeometryFilter_2
    FAILED -> Output_2 (output)
    FAILED -> Box_edficacao_rotacionado_2 [Bufferer_7_Input]
GeometryFilter_2
    FILTER_MODE = SIMPLE
    FILTER_MULTI = FILTER_TYPES]Point]FME_CONTROLLER_QUERY_FILE]]FME_CONTROLLER_CHOICE]Simple
    Point -> AttributeKeeper_19
    Point -> Box_edficacao_rotacionado_2 [Bufferer_7_Input]
    Point -> Output (output)
AttributeKeeper_19
    CREATE_BULK_MODE_FEATURES = NO
    KEEP_ATTRS = _largura_edif,_visivel,_x_original,_y_original,fme_feature_type,id,rotacao,_geometry_original
    -> Output (output) [off]
    -> AttributeKeeper_19_Output
Output (output)
AttributeKeeper_19_Output: Inspector [off]
Box_edficacao_rotacionado_2 [off]
    ROTACAO = @Value(rotacao)
    _LARGURA_EDIF = @Value(_largura_edif)
    _X_ORIGINAL = @Value(_x_original)
    _Y_ORIGINAL = @Value(_y_original)
    Rotator_2_Rotated -> casa [off]
casa: Inspector [off]
    TACKATTRS = _visivel
Output_2 (output)
Displacer_Displaced: Inspector [off]
Displacer_Untouched: Inspector [off]
Displacer_InvalidBase: Inspector [off]
Displacer_InvalidCandidate: Inspector [off]
Displacer_ExtraBase: Inspector [off]
PointOnAreaOverlayer_2_Point: Inspector [off]
Tester_11_Failed: Inspector [off]
edifi: Inspector [off]
