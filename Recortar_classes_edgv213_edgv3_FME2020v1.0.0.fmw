FME workspace Recortar_classes_edgv213_edgv3_FME2020v1.0.0.fmw

Parameters:
- EPSG = EPSG:31984
- Features_para_Recorte = sertao_sirgas_geo_DSGTOOLS3   # Database
- classes_para_recorte = cb.hid_massa_dagua_a cb.hid_trecho_drenagem_l cb.hid_trecho_massa_dagua_a cb.loc_cidade_p cb.loc_vila_p cb.tra_trecho_ferroviario_l cb.tra_trecho_rodoviario_l
- JsonMapeamento = C:\Marcos_Batista\Conversao_modelagens\modelagens-master\conversao_modelagens\arquivos_mapeamento\conversao_pg-edgv-213_pg-edgv-300.json   # Arquivo de mapeamento
- direcao = ida   # Direção do mapeamento
- SourceDataset_POSTGIS_8 = template_edgv_3   # Database 300
- DestDataset_OGCGEOPACKAGE_9 = $(FME_MF_DIR)sertao_recorte\edgv3.0.gpkg   # GeoPackage File
- DestDataset_OGCGEOPACKAGE_7 = $(FME_MF_DIR)sertao_recorte   # GeoPackage File
- DestDataset_OGCGEOPACKAGE_6 = $(FME_MF_DIR)sertao_recorte   # GeoPackage File
- DestDataset_OGCGEOPACKAGE_8 = $(FME_MF_DIR)sertao_recorte   # GeoPackage File
- SourceDataset_POSTGIS_7 = Controle_PE   # Database
- FEATURE_TYPES = public.cartas

Readers:
- POSTGIS_3: POSTGIS from $(SourceDataset_POSTGIS_7)
- POSTGIS_4: POSTGIS from $(Features_para_Recorte)
- POSTGIS_6: POSTGIS from $(SourceDataset_POSTGIS_8) in EPSG:31984

Writers:
- OGCGEOPACKAGE_2: OGCGEOPACKAGE to $(DestDataset_OGCGEOPACKAGE_9) in EPSG:31984
- OGCGEOPACKAGE_3: OGCGEOPACKAGE to $(DestDataset_OGCGEOPACKAGE_7) in EPSG:31984
- OGCGEOPACKAGE_4: OGCGEOPACKAGE to $(DestDataset_OGCGEOPACKAGE_6) in EPSG:31984
- OGCGEOPACKAGE_5: OGCGEOPACKAGE to $(DestDataset_OGCGEOPACKAGE_8) in EPSG:31984

Note: Molduras para recorte
cartas (reader POSTGIS_3)
    attributes: id int8,PrimaryKey, mi varchar(80), bloco varchar(80), status varchar(80), editor varchar(80), inicioedicao varchar(80), terminoedicao varchar(80), revisor1 varchar(80), inicio1rev varchar(80), termino1rev varchar(80), servidor varchar(80), niveis varchar(200), densidade varchar(200), revisor2 varchar(80), inicio2rev varchar(80), termino2rev varchar(80), nome_carta varchar(80), inom text, iniciocorrecao1 varchar(80), terminocorrecao1 varchar(80), iniciocorrecao2 varchar(80), terminocorrecao2 varchar(80), impressa bool, ligacao bool, totalobj varchar(200), total_p numeric(20,0), total_l numeric(20,0), total_a numeric(20,0), txt_p numeric(20,0), txt_l varchar(200),
      o varchar(80), s varchar(80), se varchar(80), so varchar(80), l varchar(80), n varchar(80), no varchar(80), ne varchar(80), linha int2, coluna int2, regiao text, corretor1 int4, corretor2 int4, CQ1 int4, CQ2 int4, inicioCQ1 text, inicioCQ2 text, terminoCQ1 text, terminoCQ2 text, AdVet int4, RevHid int4, AqHid int4, inicioRevHid text, inicioAdVet text, inicioAqHid text, terminoRevHid text, terminoAdVet text, terminoAqHid text, prioridade bool
    -> AttributeKeeper
AttributeKeeper
    KEEP_ATTRS = mi
    -> Clipper_3 [CLIPPER]
Note: Feições para serem recortadas
hid_massa_dagua_a (reader POSTGIS_4)
    attributes: id serial, geometriaaproximada int2, nome varchar(255), nomeabrev varchar(255), regime int2, salinidade int2, tipomassadagua int2, administracao int2, bitola int2, caladomax float4, canteirodivisorio int2, capaccarga float4, cargasuportmaxima float4, codtrechoferrov varchar(255), codtrechorodov varchar(255), coincidecomdentrode int2, compartilhado int2, concessionaria varchar(255), dentrodepoligono int2, eixoprincipal int2, eletrificada int2, emarruamento int2, identificador varchar(255), jurisdicao int2, larguramedia float4, latitude varchar(255), longitude varchar(255), navegabilidade int2, nrfaixas int4, nrlinhas int2,
      nrpistas int4, operacional int2, posicaorelativa int2, profundidademedia float4, revestimento int2, situacaofisica int2, tipotrechoferrov int2, tipotrechomassa int2, tipotrechorod int2, trafego int2, velocidademedcorrente float4
    -> Clipper_3 [CLIPPEE]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Reprojector_3
Reprojector_3
    DEST = $(EPSG)
    INTERPOLATION_TYPE_NAME = Nearest Neighbor
    RASTER_CELL_SIZE = Preserve Cells
    RASTER_TOLERANCE = 0.0
    SOURCE = Read from feature
    REPROJECTED -> PythonCaller_EDGV3
Note: mapeamento
PythonCaller_EDGV3
    NEW_ATTRIBUTES = CLASS_NOT_FOUND
    PYTHONSOURCE:
      import fme
      import fmeobjects
      import copy
      import sys
      import os
      import json

      class FeatureProcessor(object):
          def __init__(self):
              self.mappingDict = self.buildFileDict(FME_MacroValues['JsonMapeamento'])
              self.mappingType = FME_MacroValues['direcao']

          def buildFileDict(self, mappingPath):
              with open(mappingPath, 'r') as file:
                  mapDict = json.loads(file.read())
              return mapDict

          def buildFeatureDict(self, feature):
              featDict = dict()
              for attr in feature.getAllAttributeNames():
                  if attr == 'fme_feature_type' or ('multi_writer' not in attr and 'multi_reader_' not in attr and 'fme_' not in attr and 'postgis_' not in attr):
                      if feature.getAttribute(attr) or feature.getAttribute(attr) == 0:
                          if feature.getAttribute(attr) == 'f':
                              featDict[attr] = 'False'
                          elif feature.getAttribute(attr) == 't':
                              featDict[attr] = 'True'
                          else:
                              featDict[attr] = feature.getAttribute(attr)
                      else:
                          featDict[attr] = None
              if feature.performFunction('@GeometryType()') == 'fme_polygon' or feature.performFunction('@GeometryType()') == 'fme_donut':
                  featDict["$GEOM_TYPE"] = 'POLYGON'
              elif feature.performFunction('@GeometryType()') == 'fme_line':
                  featDict["$GEOM_TYPE"] = 'LINESTRING'
              elif feature.performFunction('@GeometryType()') == 'fme_point':
                  featDict["$GEOM_TYPE"] = 'POINT'
              else:
                   featDict["INVALID_GEOM"] = True
              return featDict

          def evaluateExpression(self, featDict, expression):
              return expression["nome_atributo"] in featDict and u"{0}".format(featDict[expression["nome_atributo"]]) == u"{0}".format(expression["valor"])

          def evaluateFilter(self, featDict, filter_condition):
              if "$and" in filter_condition:
                  return all([self.evaluateFilter(featDict, condition) for condition in filter_condition["$and"]])
              elif "$or" in filter_condition:
                  return any([self.evaluateFilter(featDict, condition) for condition in filter_condition["$or"]])
              elif "$not" in filter_condition:
                  return not self.evaluateFilter(featDict, filter_condition["$not"])
              else:
                  return self.evaluateExpression(featDict, filter_condition)

          def convertFeature(self, featDict):
              if self.mappingType == "ida":
                  key_attr_origin = "attr_ida"
                  key_attr_destiny = "attr_volta"
                  key_value_origin = "valor_ida"
                  key_value_destiny = "valor_volta"
                  key_default = "atributos_default_ida"
                  key_filter = "filtro_ida"
                  key_class_origin = "classe_ida"
                  key_class_destiny = "classe_volta"
                  key_group_origin = "tupla_ida"
                  key_group_destiny = "tupla_volta"
                  key_affix_origin = "afixo_geom_ida"
                  key_affix_destiny = "afixo_geom_volta"
                  key_schema_origin = "schema_ida"
                  key_schema_destiny = "schema_volta"
                  key_class_affix_origin = "com_afixo_geom_ida"
                  key_class_affix_destiny = "com_afixo_geom_volta"
                  key_class_schema_origin = "com_schema_ida"
                  key_class_schema_destiny = "com_schema_volta"
                  key_agregar = "agregar_geom_ida"
              else:
                  key_attr_origin = "attr_volta"
                  key_attr_destiny = "attr_ida"
                  key_value_origin = "valor_volta"
                  key_value_destiny = "valor_ida"
                  key_default = "atributos_default_volta"
                  key_filter = "filtro_volta"
                  key_class_origin = "classe_volta"
                  key_class_destiny = "classe_ida"
                  key_group_origin = "tupla_volta"
                  key_group_destiny = "tupla_ida"
                  key_affix_origin = "afixo_geom_volta"
                  key_affix_destiny = "afixo_geom_ida"
                  key_schema_origin = "schema_volta"
                  key_schema_destiny = "schema_ida"
                  key_class_affix_origin = "com_afixo_geom_volta"
                  key_class_affix_destiny = "com_afixo_geom_ida"
                  key_class_schema_origin = "com_schema_volta"
                  key_class_schema_destiny = "com_schema_ida"
                  key_agregar = "agregar_geom_volta"

              featDict["fme_feature_type_original"] = featDict["fme_feature_type"]

              if key_schema_origin in self.mappingDict and self.mappingDict[key_schema_origin]:
                  featDict["fme_feature_type"] = featDict["fme_feature_type"][len(self.mappingDict[key_schema_origin])+1:]

              featDict["fme_feature_type_sem_schema"] = featDict["fme_feature_type"]

              if key_affix_origin in self.mappingDict and 'tipo' in self.mappingDict[key_affix_origin] and self.mappingDict[key_affix_origin]['tipo'] == 'sufixo':
                  featDict["fme_feature_type"] = featDict["fme_feature_type"][:-len(self.mappingDict[key_affix_origin][featDict["$GEOM_TYPE"]])]
                  featDict["fme_feature_type_sem_afixo"] = featDict["fme_feature_type_original"][:-len(self.mappingDict[key_affix_origin][featDict["$GEOM_TYPE"]])]

              if key_affix_origin in self.mappingDict and 'tipo' in self.mappingDict[key_affix_origin] and self.mappingDict[key_affix_origin]['tipo'] == 'prefixo':
                  featDict["fme_feature_type"] = featDict["fme_feature_type"][len(self.mappingDict[key_affix_origin][featDict["$GEOM_TYPE"]]):]
                  featDict["fme_feature_type_sem_afixo"] = featDict["fme_feature_type_original"][len(self.mappingDict[key_affix_origin][featDict["$GEOM_TYPE"]]):]

              should_map = False
              for classmap in self.mappingDict['mapeamento_classes']:
                  if "sentido" not in classmap or ("sentido" in classmap and classmap["sentido"] == self.mappingType):
                      if key_class_affix_origin in classmap and classmap[key_class_affix_origin] and key_class_schema_origin in classmap and classmap[key_class_schema_origin]:
                          class_name = featDict["fme_feature_type_original"]
                      elif key_class_affix_origin in classmap and classmap[key_class_affix_origin]:
                          class_name = featDict["fme_feature_type_sem_schema"]
                      elif key_class_schema_origin in classmap and classmap[key_class_schema_origin]:
                          class_name = featDict["fme_feature_type_sem_afixo"]
                      else:
                           class_name = featDict["fme_feature_type"]

                      if classmap[key_class_origin] == class_name:
                          if key_filter in classmap:
                              if not self.evaluateFilter(featDict, classmap[key_filter]):
                                  continue
                          should_map = True
              if not should_map:
                  featDict["CLASS_NOT_FOUND"] = True
                  return featDict

              mappedFeat = copy.deepcopy(featDict)

              if key_default in self.mappingDict:
                  for default in self.mappingDict[key_default]:
                      mappedFeat[default["nome_atributo"]] = default["valor"]

              if 'mapeamento_atributos' in self.mappingDict:
                  for attmap in self.mappingDict['mapeamento_atributos']:
                      if attmap[key_attr_origin] in featDict:
                          mappedFeat[attmap[key_attr_destiny]] = featDict[attmap[key_attr_origin]]
                          if "traducao" in attmap:
                              for valuemap in attmap["traducao"]:
                                  if u"{0}".format(valuemap[key_value_origin]) == u"{0}".format(featDict[attmap[key_attr_origin]]) and ("sentido" not in valuemap or ("sentido" in valuemap and valuemap["sentido"] == self.mappingType)):
                                      mappedFeat[attmap[key_attr_destiny]] = valuemap[key_value_destiny]

              if 'mapeamento_classes' in self.mappingDict:
                  for classmap in self.mappingDict['mapeamento_classes']:
                      if "sentido" not in classmap or ("sentido" in classmap and classmap["sentido"] == self.mappingType):
                          if key_class_affix_origin in classmap and classmap[key_class_affix_origin] and key_class_schema_origin in classmap and classmap[key_class_schema_origin]:
                              class_name = featDict["fme_feature_type_original"]
                          elif key_class_affix_origin in classmap and classmap[key_class_affix_origin]:
                              class_name = featDict["fme_feature_type_sem_schema"]
                          elif key_class_schema_origin in classmap and classmap[key_class_schema_origin]:
                              class_name = featDict["fme_feature_type_sem_afixo"]
                          else:
                              class_name = featDict["fme_feature_type"]

                          if classmap[key_class_origin] == class_name:
                              if key_filter in classmap:
                                  if not self.evaluateFilter(featDict, classmap[key_filter]):
                                      continue

                              mappedFeat["fme_feature_type"] = classmap[key_class_destiny]

                              if key_class_affix_destiny in classmap and classmap[key_class_affix_destiny]:
                                  pass
                              elif key_affix_destiny in self.mappingDict and 'tipo' in self.mappingDict[key_affix_destiny]:
                                  if self.mappingDict[key_affix_destiny]['tipo'] == 'sufixo':
                                      mappedFeat["fme_feature_type"] = mappedFeat["fme_feature_type"] + self.mappingDict[key_affix_destiny][featDict["$GEOM_TYPE"]]

                                  if self.mappingDict[key_affix_destiny]['tipo'] == 'prefixo':
                                      mappedFeat["fme_feature_type"] = self.mappingDict[key_affix_destiny][featDict["$GEOM_TYPE"]] + mappedFeat["fme_feature_type"]

                              if key_class_schema_destiny in classmap and classmap[key_class_schema_destiny]:
                                  pass
                              elif key_schema_destiny in self.mappingDict and self.mappingDict[key_schema_destiny]:
                                  mappedFeat["fme_feature_type"] = self.mappingDict[key_schema_destiny] + '.' + mappedFeat["fme_feature_type"]


                              if key_default in classmap:
                                  for default in classmap[key_default]:
                                      mappedFeat[default["nome_atributo"]] = default["valor"]

                              if "mapeamento_atributos" in classmap:
                                  for attmap in classmap['mapeamento_atributos']:
                                      if attmap[key_attr_origin] in featDict:
                                          if attmap[key_attr_destiny] not in mappedFeat:
                                              mappedFeat[attmap[key_attr_destiny]] = featDict[attmap[key_attr_origin]]
                                          if "traducao" in attmap:
                                              for valuemap in attmap["traducao"]:
                                                  if u"{0}".format(valuemap[key_value_origin]) == u"{0}".format(featDict[attmap[key_attr_origin]]) and ("sentido" not in valuemap or ("sentido" in valuemap and valuemap["sentido"] == self.mappingType)):
                                                      mappedFeat[attmap[key_attr_destiny]] = valuemap[key_value_destiny]

                              if "mapeamento_multiplo" in classmap:
                                  for attmap in classmap['mapeamento_multiplo']:
                                      if "sentido" not in attmap or ("sentido" in attmap and attmap["sentido"] == self.mappingType):
                                          if all([self.evaluateExpression(featDict, condition) for condition in attmap[key_group_origin]]):
                                              for valuemap in attmap[key_group_destiny]:
                                                  if "concatenar" in valuemap and valuemap["concatenar"] and valuemap["nome_atributo"] in mappedFeat and mappedFeat[valuemap["nome_atributo"]]:
                                                      mappedFeat[valuemap["nome_atributo"]] = mappedFeat[valuemap["nome_atributo"]] + ' | ' + valuemap["valor"]
                                                  else:
                                                      mappedFeat[valuemap["nome_atributo"]] = valuemap["valor"]

                              if key_agregar in classmap:
                                  mappedFeat["AGGREGATE_GEOM"] = classmap[key_agregar]
                              elif key_agregar in self.mappingDict:
                                  mappedFeat["AGGREGATE_GEOM"] = self.mappingDict[key_agregar]

                              break

              return mappedFeat

          def mapDictToFeature(self, feat, featDict):
              for attr, value in featDict.items():
                  if value or value == 0:
                      feat.setAttribute(attr, u'{0}'.format(value))
                  else:
                      feat.setAttributeNullWithType(attr,0)
              if "AGGREGATE_GEOM" in featDict and featDict["AGGREGATE_GEOM"]:
                  feat.buildAggregateFeat([feat])
              return feat

          def input(self,feature):
              if feature.performFunction('@GeometryType()') == 'fme_aggregate':
                  features = feature.splitAggregate(True)
              else:
                  features = [feature]
              for simple_feature in features:
                  feat = self.buildFeatureDict(simple_feature)
                  if "INVALID_GEOM" in feat and not feat["INVALID_GEOM"]:
                      simple_feature.setAttribute("INVALID_GEOM", u'True')
                      self.pyoutput(simple_feature)
                      continue

                  outputFeatDict = self.convertFeature(feat)
                  if "CLASS_NOT_FOUND" in outputFeatDict and not outputFeatDict["CLASS_NOT_FOUND"]:
                      simple_feature.setAttribute("CLASS_NOT_FOUND", u'True')
                      self.pyoutput(simple_feature)
                  else:
                      outputFeature = self.mapDictToFeature(simple_feature, outputFeatDict)
                      self.pyoutput(outputFeature)

          def close(self):
              pass
    PYTHONSYMBOL = FeatureProcessor
    -> Tester_4
Note: Teste de mapeamento
Tester_4
    BOOL_OP = OR
    TEST_CLAUSE = TEST @Value(CLASS_NOT_FOUND) = True
    TEST_MODE = TEST
    PASSED -> DuplicateFilter
    FAILED -> Counter
DuplicateFilter
    INPUT_ORDERED_CHOICE = No
    KEYATTR = fme_feature_type
    UNIQUE -> CLASS_NOT_FOUND
CLASS_NOT_FOUND: Inspector
Counter
    CNT_ATTR = id
    DOMAIN = @Value(fme_feature_type)
    SCOPE = Global
    START = 1
    -> AttributeRemover
AttributeRemover
    REMOVE_ATTRS = _clipped,CLASS_NOT_FOUND
    -> Reprojector_4
Reprojector_4
    DEST = EPSG:31984
    INTERPOLATION_TYPE_NAME = Nearest Neighbor
    RASTER_CELL_SIZE = Preserve Cells
    RASTER_TOLERANCE = 0.0
    SOURCE = Read from feature
    REPROJECTED -> GeometryFilter
    REPROJECTED -> gravar
GeometryFilter
    BREAK_AGG = No
    GEOM_PORT_NAMES = Point Area Line
    POINT -> Table1 (writer OGCGEOPACKAGE_3)
    AREA -> Table1 (writer OGCGEOPACKAGE_5)
    LINE -> Table1 (writer OGCGEOPACKAGE_4)
Note: Table1: p_edgv3 [OGCGEOPACKAGE]
Table1 (writer OGCGEOPACKAGE_3)
    attributes: mi text(80), id mediumint, geometriaaproximada smallint, nome text(255), nomeabrev text(255), regime smallint, salinidade smallint, tipomassadagua smallint, administracao smallint, bitola smallint, caladomax float, canteirodivisorio smallint, capaccarga float, cargasuportmaxima float, codtrechoferrov text(255), codtrechorodov text(255), coincidecomdentrode smallint, compartilhado smallint, concessionaria text(255), dentrodepoligono smallint, eixoprincipal smallint, eletrificada smallint, emarruamento smallint, identificador text(255), jurisdicao smallint, larguramedia float, latitude text(255), longitude text(255), navegabilidade smallint, nrfaixas mediumint,
      nrlinhas smallint, nrpistas mediumint, operacional smallint, posicaorelativa smallint, profundidademedia float, revestimento smallint, situacaofisica smallint, tipotrechoferrov smallint, tipotrechomassa smallint, tipotrechorod smallint, trafego smallint, velocidademedcorrente float
Note: Table1: a_edgv3 [OGCGEOPACKAGE]
Table1 (writer OGCGEOPACKAGE_5)
    attributes: mi text(80), id mediumint, geometriaaproximada smallint, nome text(255), nomeabrev text(255), regime smallint, salinidade smallint, tipomassadagua smallint, administracao smallint, bitola smallint, caladomax float, canteirodivisorio smallint, capaccarga float, cargasuportmaxima float, codtrechoferrov text(255), codtrechorodov text(255), coincidecomdentrode smallint, compartilhado smallint, concessionaria text(255), dentrodepoligono smallint, eixoprincipal smallint, eletrificada smallint, emarruamento smallint, identificador text(255), jurisdicao smallint, larguramedia float, latitude text(255), longitude text(255), navegabilidade smallint, nrfaixas mediumint,
      nrlinhas smallint, nrpistas mediumint, operacional smallint, posicaorelativa smallint, profundidademedia float, revestimento smallint, situacaofisica smallint, tipotrechoferrov smallint, tipotrechomassa smallint, tipotrechorod smallint, trafego smallint, velocidademedcorrente float
Note: Table1: l_edgv3 [OGCGEOPACKAGE]
Table1 (writer OGCGEOPACKAGE_4)
    attributes: mi text(80), id mediumint, geometriaaproximada smallint, nome text(255), nomeabrev text(255), regime smallint, salinidade smallint, tipomassadagua smallint, administracao smallint, bitola smallint, caladomax float, canteirodivisorio smallint, capaccarga float, cargasuportmaxima float, codtrechoferrov text(255), codtrechorodov text(255), coincidecomdentrode smallint, compartilhado smallint, concessionaria text(255), dentrodepoligono smallint, eixoprincipal smallint, eletrificada smallint, emarruamento smallint, identificador text(255), jurisdicao smallint, larguramedia float, latitude text(255), longitude text(255), navegabilidade smallint, nrfaixas mediumint,
      nrlinhas smallint, nrpistas mediumint, operacional smallint, posicaorelativa smallint, profundidademedia float, revestimento smallint, situacaofisica smallint, tipotrechoferrov smallint, tipotrechomassa smallint, tipotrechorod smallint, trafego smallint, velocidademedcorrente float
gravar: Inspector
Note: Banco Esquema edgv 3.0
aquisicao_centroide_area_construida_p (reader POSTGIS_6) [off]
    attributes: id serial, nome varchar(255), densamente_edificada int2, observacao varchar(255), data_modificacao timestamptz, controle_uuid varchar(255), usuario_criacao varchar(255), usuario_atualizacao varchar(255), insumo varchar(255), data_insumo timestamptz, administracao int2, altitude_geometrica varchar(255), altitude_ortometrica varchar(255), canteiro_divisorio int2, cod_ponto varchar(255), concessionaria varchar(255), corrigido bool, cota int4, cota_comprovada int2, depressao int2, descricao varchar(255), em_arruamento int2, finalidade int2, fonte varchar(255), forma_extracao int2, geometria_aproximada int2, indice int2, jurisdicao int2, justificativa varchar(255), latitude varchar(255),
      longitude varchar(255), material_construcao int2, modal_uso int2, nr_faixas varchar(255), nr_linhas int2, nr_pistas varchar(255), orgao_responsavel varchar(255), posicao_pista int2, posicao_relativa int2, referencial_altim int2, referencial_grav int2, regime int2, revestimento int2, sigla varchar(255), sistema_geodesico int2, situacao_fisica int2, situacao_marco int2, subfase_id int4, tipo int2, tipo_delimitacao int2, tipo_exposicao int2, tipo_ref int2, trafego int2, uso_pista int2
    -> modelo_edgv3.0
modelo_edgv3.0: Inspector
