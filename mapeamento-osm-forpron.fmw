FME workspace mapeamento-osm-forpron.fmw

Parameters:
- SourceDataset_OGCGEOPACKAGE = ""Z:\DGEO\MAPEAMENTO_PE\7DE_FORPRON_2023\COMBATER-2023-OSM\1211.gpkg" "Z:\DGEO\MAPEAMENTO_PE\7DE_FORPRON_2023\COMBATER-2023-OSM\1211-massa-dagua.gpkg" "Z:\DGEO\MAPEAMENTO_PE\7DE_FORPRON_2023\COMBATER-2023-OSM\1212.gpkg" "Z:\DGEO\MAPEAMENTO_PE\7DE_FORPRON_2023\COMBATER-2023-OSM\1212-massa-dagua.gpkg" "Z:\DGEO\MAPEAMENTO_PE\7DE_FORPRON_2023\COMBATER-2023-OSM\1213.gpkg" "Z:\DGEO\MAPEAMENTO_PE\7DE_FORPRON_2023\COMBATER-2023-OSM\1213-massa-dagua.gpkg" "Z:\DGEO\MAPEAMENTO_PE\7DE_FORPRON_2023\COMBATER-2023-OSM\1290.gpkg" "Z:\DGEO\MAPEAMENTO_PE\7DE_FORPRON_2023\COMBATER-2023-OSM\1290-massa-dagua.gpkg" "Z:\DGEO\MAPEAMENTO_PE\7DE_FORPRON_2023\COMBATER-2023-OSM\1291.gpkg" "Z:\DGEO\MAPEAMENTO_PE\7DE_FORPRON_2023\COMBATER-2023-OSM\1291-massa-dagua.gpkg" "Z:\DGEO\MAPEAMENTO_PE\7DE_FORPRON_2023\COMBATER-2023-OSM\1292.gpkg" "Z:\DGEO\MAPEAMENTO_PE\7DE_FORPRON_2023\COMBATER-2023-OSM\1292-massa-dagua.gpkg" "Z:\DGEO\MAPEAMENTO_PE\7DE_FORPRON_2023\COMBATER-2023-OSM\1369.gpkg" "Z:\DGEO\MAPEAMENTO_PE\7DE_FORPRON_2023\COMBATER-2023-OSM\1369-massa-dagua.gpkg" "Z:\DGEO\MAPEAMENTO_PE\7DE_FORPRON_2023\COMBATER-2023-OSM\1370.gpkg" "Z:\DGEO\MAPEAMENTO_PE\7DE_FORPRON_2023\COMBATER-2023-OSM\1370-massa-dagua.gpkg" "Z:\DGEO\MAPEAMENTO_PE\7DE_FORPRON_2023\COMBATER-2023-OSM\1371.gpkg" "Z:\DGEO\MAPEAMENTO_PE\7DE_FORPRON_2023\COMBATER-2023-OSM\1371-massa-dagua.gpkg""   # GeoPackage File
- FEATURE_TYPES = 1211 1211-massa-dagua 1212 1212-massa-dagua 1213 1213-massa-dagua 1290 1290-massa-dagua 1291 1291-massa-dagua 1292 1292-massa-dagua 1369 1369-massa-dagua 1370 1370-massa-dagua 1371 1371-massa-dagua
- SourceDataset_OGCGEOPACKAGE_3 = Z:\DGEO\MAPEAMENTO_PE\7DE_FORPRON_2023\area_recorte_mapeamento_pe.gpkg   # GeoPackage File
- FEATURE_TYPES_2 =
- DestDataset_POSTGIS = Combater_2023   # Database
- DestDataset_OGCGEOPACKAGE_2 = Z:\DGEO\MAPEAMENTO_PE\7DE_FORPRON_2023\OSM_Forpron.gpkg   # GeoPackage File

Readers:
- OGCGEOPACKAGE_1: OGCGEOPACKAGE from $(SourceDataset_OGCGEOPACKAGE)
- OGCGEOPACKAGE_2: OGCGEOPACKAGE from $(SourceDataset_OGCGEOPACKAGE_3)

Writers:
- POSTGIS_1: POSTGIS to $(DestDataset_POSTGIS)
- OGCGEOPACKAGE_4: OGCGEOPACKAGE to $(DestDataset_OGCGEOPACKAGE_2) in EPSG:4674

Note: : area_recorte_mapeamento_pe [OGCGEOPACKAGE]
area_recorte_mapeamento_pe (reader OGCGEOPACKAGE_2)
    attributes: id mediumint, mi text(10), carta_nome text(40), aq_respvl text(15), aq_ini date, aq_fim date, val_respvl text(15), val_ini date, val_fim date, area_cont_respvl text(15), area_cont_ini date, area_cont_fim date, ed_respvl text(15), ed_ini date, ed_fim date, fid int,PrimaryKey
    -> Reprojector_2
Reprojector_2
    DEST = EPSG:4674
    INTERPOLATION_TYPE_NAME = Nearest Neighbor
    RASTER_CELL_SIZE = Preserve Cells
    RASTER_TOLERANCE = 0.0
    REPROJECTED -> Clipper [CLIPPER]
Note: : 1211/1211-massa-dagua/1212/1212-massa-dagua/1213/1213-massa-dagua/1290/1290-massa-dagua/1291/1291-massa-dagua/1292/1292-massa-dagua/1369/1369-massa-dagua/1370/1370-massa-dagua/1371/1371-massa-dagua [OGCGEOPACKAGE]
1211 (reader OGCGEOPACKAGE_1)
    attributes: osm_id text, name text, highway text, waterway text, aerialway text, barrier text, man_made text, railway text, z_order mediumint, other_tags text, fid int,PrimaryKey, admin_level text, aeroway text, amenity text, boundary text, building text, craft text, geological text, historic text, land_area text, landuse text, leisure text, military text, natural text, office text, osm_way_id text, place text, shop text, sport text, tourism text,
      type text
    -> _All_
    -> Reprojector
_All_: Inspector
Reprojector
    DEST = EPSG:4674
    INTERPOLATION_TYPE_NAME = Nearest Neighbor
    RASTER_CELL_SIZE = Preserve Cells
    RASTER_TOLERANCE = 0.0
    REPROJECTED -> AttributeCreator
AttributeCreator
    ATTR_TABLE:
      SET_TO MI-100 = @Left(@Value(fme_feature_type),4)
      SET_TO base_dados = @Value(fme_feature_type)
      SET_TO fme_feature_type = FME_CONDITIONAL:DEFAULT_VALUE'_FME_NO_OP_'BOOL_OP;AND;COMPOSITE_TEST;1 AND 2;TEST waterway ATTRIBUTE_HAS_A_VALUE _FME_BLANK_STRING_;TEST @Value(waterway) != dam'base_rio_l'BOOL_OP;OR;COMPOSITE_TEST;1;CASE_INSENSITIVE_TEST @Value(base_dados) CONTAINS massa-dagua'base_cob_ter_a'BOOL_OP;AND;COMPOSITE_TEST;1;CASE_INSENSITIVE_TEST highway ATTRIBUTE_HAS_A_VALUE _FME_BLANK_STRING_'base_estrada_l'FME_NUM_CONDITIONS4___
      SET_TO descricao = OSM_@Left(@Value(other_tags),75)
      SET_TO identificador_osm = @UUID()
    -> AttributeFilter
AttributeFilter
    ATTR_NAME = fme_feature_type
    ATTR_VALUES = <Empty>,<Missing>,<Null>,<Unfiltered>,base_cob_ter_a,base_rio_l,base_estrada_l
    base_cob_ter_a -> AttributeCreator_4
    base_rio_l -> AttributeCreator_3
    base_estrada_l -> AttributeCreator_2
AttributeCreator_4
    ATTR_TABLE = SET_TO CAMADAS COMBATER = WATER_AREA
    -> Clipper [CANDIDATE]
AttributeCreator_3
    ATTR_TABLE = SET_TO CAMADAS COMBATER = FME_CONDITIONAL:DEFAULT_VALUE'SMALL_RIVER'BOOL_OP;OR;COMPOSITE_TEST;1;CASE_INSENSITIVE_TEST name ATTRIBUTE_HAS_A_VALUE _FME_BLANK_STRING_'LARGE_RIVER'FME_NUM_CONDITIONS2___
    -> Clipper [CANDIDATE]
AttributeCreator_2
    ATTR_TABLE = SET_TO CAMADAS COMBATER = FME_CONDITIONAL:DEFAULT_VALUE'SMALL_ROAD'BOOL_OP;OR;COMPOSITE_TEST;1 OR 2;CASE_INSENSITIVE_TEST @Value(descricao) CONTAINS federal;CASE_INSENSITIVE_TEST @Value(descricao) CONTAINS estadual'LARGE_ROAD'FME_NUM_CONDITIONS2___
    -> Aggregator
Aggregator
    ACCUM_ATTRS_NAME = Use Attributes From One Feature
    AGGREGATE_TYPE = Heterogeneous Collection
    GROUP_BY = identificador_osm
    MODE = Geometry - Assemble One Level
    SEP = ,
    AGGREGATE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeKeeper
AttributeKeeper
    CREATE_BULK_MODE_FEATURES = NO
    KEEP_ATTRS = descricao,fme_feature_type,MI-100,name,CAMADAS COMBATER
    -> AttributeKeeper_Output
    -> Table1 (writer POSTGIS_1)
    -> Table1 (writer OGCGEOPACKAGE_4)
AttributeKeeper_Output: Inspector
    TACKATTRS = fme_feature_type
Table1 (writer POSTGIS_1) [off]
Table1 (writer OGCGEOPACKAGE_4)
