FME workspace mapeamento_modelagem_para_forpron.fmw

Parameters:
- SourceDataset_POSTGIS = mapeamento_pe_25k_30   # Database
- FEATURE_TYPES = edgv.fer_trecho_ferroviario_l edgv.hid_banco_areia_a edgv.hid_ilha_a edgv.hid_massa_dagua_a edgv.hid_trecho_drenagem_l edgv.rel_alteracao_fisiografica_antropica_a edgv.rel_elemento_fisiografico_natural_a edgv.rel_ponto_cotado_altimetrico_p edgv.rel_rocha_a edgv.rel_terreno_exposto_a edgv.rod_trecho_rodoviario_l edgv.tra_caminho_carrocavel_l edgv.tra_ponte_l edgv.tra_tunel_l edgv.veg_brejo_pantano_a edgv.veg_caatinga_a edgv.veg_campinarana_a edgv.veg_campo_a edgv.veg_cerrado_a edgv.veg_floresta_a edgv.veg_mangue_a edgv.veg_reflorestamento_a edgv.veg_veg_area_contato_a edgv.veg_veg_cultivada_a edgv.veg_veg_restinga_a edgv.rel_curva_nivel_l
- SourceDataset_OGCGEOPACKAGE = C:\Marcos_Batista\DGEO\FORPRON\Forpron_2023\area_recorte_mapeamento_pe.gpkg   # GeoPackage File
- FEATURE_TYPES_2 =
- DestDataset_POSTGIS = Combater_2023   # Database

Readers:
- POSTGIS_1: POSTGIS from $(SourceDataset_POSTGIS)
- OGCGEOPACKAGE_1: OGCGEOPACKAGE from $(SourceDataset_OGCGEOPACKAGE)

Writers:
- POSTGIS_2: POSTGIS to $(DestDataset_POSTGIS)

Note: : area_recorte_mapeamento_pe [OGCGEOPACKAGE]
area_recorte_mapeamento_pe (reader OGCGEOPACKAGE_1)
    attributes: id mediumint, mi text(10), carta_nome text(40), aq_respvl text(15), aq_ini date, aq_fim date, val_respvl text(15), val_ini date, val_fim date, area_cont_respvl text(15), area_cont_ini date, area_cont_fim date, ed_respvl text(15), ed_ini date, ed_fim date, fid int,PrimaryKey
    -> Clipper [CLIPPER]
Note: : mapeamento_pe_25k_30 [POSTGIS]
aer_pista_ponto_pouso_a (reader POSTGIS_1)
    attributes: id serial, nome varchar(80), geometriaaproximada bool, tipopista int2, revestimento int2, usopista int2, homologacao int2, operacional int2, situacaofisica int2, largura float4, extensao float4, altitude float4, acostamento bool, administracao int2, altitudegeometrica float4, altitudeortometrica float4, altura float4, alturaaproximada float4, alturaestimada float4, alturalamina float4, alturatorreaer float4, anocriacao varchar(4), anodereferencia int4, antropizada int2, aptidaooperacional int2, arealegal float4, areaoficial varchar(15), areavalvulas bool, artificial int2, atividade int2,
      atolegal varchar(100), bitola int2, bombeamento bool, calado float4, caladomaxseca float4, calcada int2, canteirodivisorio int2, cargasuportmaxima float4, causa int2, causaexposicao int2, ceg varchar(16), centrodecarga int2, chamine int2, classeativecon int2, classificacao varchar(100), classificacaoporte int2, codequipdesenvsocial varchar(80), codestacao varchar(50), codident varchar(80), codidentificadorunico varchar(50), codigo varchar(9), codiso3166 varchar(3), codponto varchar(9), codtrechoferrov varchar(25), codtrechorod varchar(25), coletiva int2, concessionaria varchar(100), cota int4, cotacomprovada bool, crista bool,
      cultivopredominante int2, cultura int2, datamedicao varchar(10), datasituacaojuridica varchar(10), datavisita varchar(10), denominacaoassociada int2, densidade int2, depressao bool, desnivel float4, destinacaocemiterio int2, destinadoa int2, dominialidade int2, eletrificada int2, emarruamento bool, emduto bool, encoberto bool, ensino int2, escala varchar(255), especie int2, especiepredominante int2, estadofisico int2, extensaotrecho float4, finalidade int2, finalidadedep int2, finalidadepatio int2, fixa bool, formaextracao int2, formarocha int2, gabhorizsup float4, gabvertsup float4,
      geocodigo varchar(15), grupoetnico varchar(100), historicomodificacoes varchar(255), identificador varchar(80), idtsub int4, inom varchar(255), isolada int2, jurisdicao int2, largurafaixaservidao float4, larguramedia float4, latitude varchar(15), length float4, limitevelocidade float4, localizacaoequipdesenvsocial int2, longitude varchar(15), matcondutor int2, matconstr int2, materialpredominante int2, mattransp int2, meiofio bool, mi varchar(255), modalidade int2, modaluso int2, navegavel int2, necessitamanutencao int2, nivelatencao int2, nomelocal varchar(80), nrdutos int4, nrfaixas int4, nrlinhas int2,
      nrpistas int4, obs varchar(255), orgaoenteresp varchar(15), outrarefalt varchar(20), outrarefplan varchar(20), ovgd int2, pavimentacao int2, perimetrooficial float4, periodicidadeinunda varchar(20), pesosuportmaximo float4, posicaopista int2, posicaorelativa int2, posicaoreledific int2, possuitrechodrenagem bool, potenciaout float4, procextracao int2, profundidade int4, proximidade int2, publico bool, qualidagua int2, redereferencia int2, referencialaltim int2, referencialgrav int2, regime int2, religiao varchar(100), salgada int2, sarjeta bool, secaoativecon int2, secundaria int2, setor int2,
      sigla varchar(80), sin int2, sistemageodesico int2, situacaoagua int2, situacaocosta int2, situacaoemagua int2, situacaoespacial int2, situacaojuridica int2, situacaomarco int2, terreno int2, tipoahe int2, tipoalterantrop int2, tipoarea int2, tipoareaumida int2, tipoassociado int2, tipoatracad int2, tipobanco int2, tipocaminhoaereo int2, tipocampo int2, tipocampoquadra int2, tipocemiterio int2, tipocombustivel int2, tipoconteudo int2, tipocurvanivel int2, tipodelimfis int2, tipodepgeral int2, tipoedifabast int2, tipoedifaero int2, tipoedifagropec int2, tipoedifcomercserv int2,
      tipoedifcomunic int2, tipoedifenergia int2, tipoediflazer int2, tipoedifmetroferrov int2, tipoedifport int2, tipoedifpubcivil int2, tipoedifrelig int2, tipoedifrod int2, tipoedifsaneam int2, tipoedifturist int2, tipoelemnat int2, tipoelevador int2, tipoembarcacao int2, tipoentroncamento int2, tipoequipagropec int2, tipoequipdesenvsocial int2, tipoestgerad int2, tipoexposicao int2, tipoextmin int2, tipofontedagua int2, tipofundeadouro int2, tipoilha int2, tipoinstalmilitar int2, tipolavoura int2, tipolocalidade int2, tipomanguezal int2, tipomarcolim int2, tipomassadagua int2, tipoobst int2, tipopassagviad int2,
      tipopavimentacao int2, tipopistacomp int2, tipoplataforma int2, tipopocomina int2, tipoponte int2, tipoposte int2, tipopostofisc int2, tipoproduto int2, tipoprodutoresiduo int2, tipoptoestmed int2, tipoptorefgeodtopo int2, tipoquebramolhe int2, tipoqueda int2, tiporecife int2, tiporef int2, tiporepdiplomatica int2, tiposinal int2, tiposumvert int2, tipoterrexp int2, tipotravessia int2, tipotravessiaped int2, tipotrechocomunic int2, tipotrechodrenagem int2, tipotrechoduto int2, tipotrechoferrov int2, tipotunel int2, tipounidprotegida int2, tipounidprotinteg int2, tipounidusosust int2, tipouso int2,
      tipousocaminhoaer int2, tipousoedif int2, tipoveg int2, tipovia int2, tombada bool, trafego int2, tratamento int2, trechoemperimetrourbano bool, turistica bool, unidadevolume int2, usoprincipal int2, valorgravidade float4, valorvolume float4, vaolivrehoriz float4, vaovertical float4, vereda int2
    -> AttributeFilter
AttributeFilter
    ATTR_NAME = fme_feature_type
    ATTR_VALUES = <Empty>,<Missing>,<Null>,<Unfiltered>,edgv.hid_massa_dagua_a,edgv.rel_ponto_cotado_altimetrico_p,edgv.rel_curva_nivel_l,edgv.fer_trecho_ferroviario_l,edgv.hid_trecho_drenagem_l,edgv.tra_caminho_carrocavel_l,edgv.rod_trecho_rodoviario_l
    <UNFILTERED> -> Tester [off]
    edgv.hid_massa_dagua_a -> AttributeCreator_2 [off]
    edgv.rel_ponto_cotado_altimetrico_p -> AttributeCreator [off]
    edgv.rel_curva_nivel_l -> AttributeCreator [off]
    edgv.fer_trecho_ferroviario_l -> AttributeCreator [off]
    edgv.hid_trecho_drenagem_l -> AttributeCreator [off]
    edgv.tra_caminho_carrocavel_l -> AttributeCreator_5
    edgv.rod_trecho_rodoviario_l -> AttributeCreator_6
Tester
    BOOL_OP = OR
    TEST_CLAUSE = TEST @Right(@Value(fme_feature_type),2) = _a
    TEST_MODE = TEST
    PASSED -> AttributeCreator_3
AttributeCreator_2
    ATTR_TABLE = SET_TO MASSA_CODE = 1004
    -> AttributeCreator_3
AttributeCreator_3
    ATTR_TABLE = SET_TO fme_feature_type = base.cob_ter_a
    -> Junction
AttributeCreator_5
    ATTR_TABLE:
      SET_TO MASACODE = 20004
      SET_TO CAMADAS COMBATER = SMALL_ROAD
      SET_TO nome = @Value(sigla)
    -> AttributeCreator
AttributeCreator_6
    ATTR_TABLE:
      SET_TO MASACODE = FME_CONDITIONAL:DEFAULT_VALUE'20003'BOOL_OP;OR;COMPOSITE_TEST;1 OR 2;TEST @Value(jurisdicao) = 1;TEST @Value(jurisdicao) = 2'20002'FME_NUM_CONDITIONS2___
      SET_TO CAMADAS COMBATER = FME_CONDITIONAL:DEFAULT_VALUE'MEDIUM_ROAD'BOOL_OP;OR;COMPOSITE_TEST;1 OR 2;TEST @Value(jurisdicao) = 1;TEST @Value(jurisdicao) = 2'LARGE_ROAD'FME_NUM_CONDITIONS2___
      SET_TO nome = @Value(sigla)
    -> AttributeCreator
Note: Mapeia classes
AttributeCreator
    ATTR_TABLE = SET_TO fme_feature_type = FME_CONDITIONAL:DEFAULT_VALUE'_FME_NO_OP_'BOOL_OP;OR;COMPOSITE_TEST;1 OR 2;TEST @Value(fme_feature_type) = edgv.tra_caminho_carrocavel_l;TEST @Value(fme_feature_type) = edgv.rod_trecho_rodoviario_l'base.estrada_l'BOOL_OP;OR;COMPOSITE_TEST;1;TEST @Value(fme_feature_type) = edgv.fer_trecho_ferroviario_l'base.ferrovia_l'BOOL_OP;OR;COMPOSITE_TEST;1;TEST @Value(fme_feature_type) = edgv.hid_trecho_drenagem_l'base.rio_l'BOOL_OP;OR;COMPOSITE_TEST;1;TEST @Value(fme_feature_type) = edgv.rel_ponto_cotado_altimetrico_p'base.ponto_cotado_altimetrico_p'BOOL_OP;OR;COMPOSITE_TEST;1;TEST @Value(fme_feature_type) = edgv.rel_curva_nivel_l'base.curva_nivel_l'FME_NUM_CONDITIONS6___
    -> Junction
Junction
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> AttributeKeeper
    OUTSIDE -> Clipper_Outside
AttributeKeeper
    CREATE_BULK_MODE_FEATURES = NO
    KEEP_ATTRS = id,fme_feature_type,MASSA_CODE,cota,cotacomprovada,CAMADAS COMBATER,nome
    -> Sorter
Sorter
    GROUP_BY = fme_feature_type
    SORT_PARM = id NUMERIC ASCENDING
    SORTED -> Counter
Counter
    CNT_ATTR = id
    DOMAIN = @Value(fme_feature_type)
    SCOPE = Global
    START = 1
    -> Tester_2
Tester_2
    BOOL_OP = OR
    TEST_CLAUSE = TEST @Value(fme_feature_type) = base.rio_l
    TEST_MODE = TEST
    PASSED -> AggregateFilter
    FAILED -> AttributeCreator_4
AggregateFilter
    AGGREGATE -> Aggregator_2
    NOT_AGGREGATE -> Aggregator_2
Aggregator_2
    ACCUM_ATTRS_NAME = Merge Incoming Attributes
    AGGREGATE_TYPE = Heterogeneous Collection
    GROUP_BY = fme_feature_type id
    MODE = Geometry - Assemble One Level
    SEP = ,
    AGGREGATE -> AttributeCreator_4
AttributeCreator_4
    ATTR_TABLE:
      SET_TO geometriaaproximada = 9999
      SET_TO cotacomprovada = 9999
      SET_TO descricao = MAPEAMENTO_PE
      SET_TO codigo = 1
    -> Table1 (writer POSTGIS_2)
    -> RESULTADO
RESULTADO: Inspector
    TACKATTRS = fme_feature_type
Note: : Combater_2023 [POSTGIS]
Table1 (writer POSTGIS_2)
Clipper_Outside: Inspector
