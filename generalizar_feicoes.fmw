FME workspace generalizar_feicoes.fmw

Parameters:
- SourceDataset_POSTGIS = ebgeo_core_multiescala   # Connection
- EPSG = EPSG:31984   # epsg
- VEG_MIN_100K = 250000
- FEATURE_TYPES = edgv.centroide_area_edificada_1m_p edgv.centroide_area_edificada_10k_p edgv.centroide_area_edificada_25k_p edgv.centroide_area_edificada_50k_p edgv.centroide_area_edificada_100k_p edgv.centroide_area_edificada_250k_p edgv.centroide_area_edificada_500k_p edgv.cobter_area_edificada_1m_a edgv.cobter_area_edificada_10k_a edgv.cobter_area_edificada_25k_a edgv.cobter_area_edificada_50k_a edgv.cobter_area_edificada_100k_a edgv.cobter_area_edificada_250k_a edgv.cobter_area_edificada_500k_a edgv.delimitador_area_edificada_1m_l edgv.delimitador_area_edificada_10k_l edgv.delimitador_area_edificada_25k_l edgv.delimitador_area_edificada_50k_l edgv.delimitador_area_edificada_100k_l edgv.delimitador_area_edificada_250k_l edgv.delimitador_area_edificada_500k_l edgv.llp_localidade_1m_p edgv.llp_localidade_10k_p edgv.llp_localidade_25k_p edgv.llp_localidade_50k_p edgv.llp_localidade_100k_p edgv.llp_localidade_250k_p edgv.llp_localidade_500k_p
- generelizar_para_ESCALA = 100
- DestDataset_POSTGIS = ebgeo_core_multiescala   # Database

Readers:
- POSTGIS_1: POSTGIS from $(SourceDataset_POSTGIS)

Writers:
- POSTGIS_2: POSTGIS to $(DestDataset_POSTGIS)

Note: : ebgeo_core_multiescala [POSTGIS]
aux_moldura_100k_a (reader POSTGIS_1)
    attributes: id uuid, nome varchar(255), mi varchar(255), inom varchar(255), observacao varchar(255), administracao_code int2, administracao_value varchar(255), altitude float4, altitude_geometrica varchar(255), altitude_ortometrica varchar(255), altura float4, ancora_horizontal_code int2, ancora_horizontal_value varchar(255), ancora_vertical_code int2, ancora_vertical_value varchar(255), assentamento_precario_code int2, assentamento_precario_value varchar(255), bitola_code int2, bitola_value varchar(255), canteiro_divisorio_code int2, canteiro_divisorio_value varchar(255), cod_ponto varchar(255), concessionaria varchar(255), config_comprimento_simb_code int2, config_comprimento_simb_value varchar(255), cor varchar(255), corrigido_code int2, corrigido_value varchar(255), cota int4, cota_comprovada_code int2,
      cota_comprovada_value varchar(255), cota_mais_alta_code int2, cota_mais_alta_value varchar(255), dentro_massa_dagua_code int2, dentro_massa_dagua_value varchar(255), depressao_code int2, depressao_value varchar(255), descricao varchar(255), desloc float4, direcao varchar(255), direcao_fixada_code int2, direcao_fixada_value varchar(255), eletrificada_code int2, eletrificada_value varchar(255), em_arruamento_code int2, em_arruamento_value varchar(255), em_galeria_bueiro_code int2, em_galeria_bueiro_value varchar(255), espacamento float4, estilo_fonte varchar(255), exibir_lado_simbologia_code int2, exibir_lado_simbologia_value varchar(255), exibir_linha_rotulo_code int2, exibir_linha_rotulo_value varchar(255), exibir_ponta_simbologia_code int2, exibir_ponta_simbologia_value varchar(255), exibir_rotulo_aproximado_code int2, exibir_rotulo_aproximado_value varchar(255), finalidade_code int2, finalidade_value varchar(255),
      forma_extracao_code int2, forma_extracao_value varchar(255), geometria_aproximada_code int2, geometria_aproximada_value varchar(255), indice_code int2, indice_value varchar(255), jurisdicao_code int2, jurisdicao_value varchar(255), justificativa varchar(255), justificativa_txt_code int2, justificativa_txt_value varchar(255), label_x float4, label_y float4, largura_simbologia float4, latitude varchar(255), longitude varchar(255), material_construcao_code int2, material_construcao_elemento_viario_code int2, material_construcao_elemento_viario_value varchar(255), material_construcao_value varchar(255), modal_uso_code int2, modal_uso_value varchar(255), nome_elemento_viario varchar(255), nr_faixas varchar(255), nr_linhas_code int2, nr_linhas_value varchar(255), nr_pistas varchar(255), numero varchar(255), ordem_simbologia int4, orgao_responsavel varchar(255),
      populacao int4, posicao_pista_code int2, posicao_pista_elemento_viario_code int2, posicao_pista_elemento_viario_value varchar(255), posicao_pista_value varchar(255), posicao_relativa_code int2, posicao_relativa_value varchar(255), posicao_rotulo_code int2, posicao_rotulo_value varchar(255), referencial_altim_code int2, referencial_altim_value varchar(255), referencial_grav_code int2, referencial_grav_value varchar(255), regime_code int2, regime_value varchar(255), revestimento_code int2, revestimento_value varchar(255), sigla varchar(255), sigla_code int2, sigla_value varchar(255), simb_rot float4, sistema_geodesico_code int2, sistema_geodesico_value varchar(255), situacao_em_poligono_code int2, situacao_em_poligono_value varchar(255), situacao_fisica_code int2, situacao_fisica_value varchar(255), situacao_marco_code int2, situacao_marco_value varchar(255), sobreposto_code int2,
      sobreposto_transportes_code int2, sobreposto_transportes_value varchar(255), sobreposto_value varchar(255), subfase_id int4, sujeito_inundacao_code int2, sujeito_inundacao_value varchar(255), suprimir_bandeira_code int2, suprimir_bandeira_value varchar(255), suprimir_simbologia_code int2, suprimir_simbologia_value varchar(255), tamanho_txt float4, texto_edicao varchar(255), tipo_code int2, tipo_elemento_viario_code int2, tipo_elemento_viario_value varchar(255), tipo_exposicao_code int2, tipo_exposicao_value varchar(255), tipo_grid varchar(255), tipo_produto_code int2, tipo_produto_value varchar(255), tipo_ref_code int2, tipo_ref_value varchar(255), tipo_value varchar(255), trafego_code int2, trafego_value varchar(255), uso_pista_code int2, uso_pista_value varchar(255), visivel_code int2, visivel_value varchar(255)
    -> PythonCaller
Note: Cria Atributos Basicos
PythonCaller
    NEW_ATTRIBUTES = escala varchar(20) fme_feature_type_origem varchar(200) geom_texto char(20)
    PYTHONSOURCE:
      import fme
      import fmeobjects


      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              # Substitua pelo nome real do seu atributo de entrada
              valor = feature.getAttribute("fme_feature_type")

              # Verifica se o valor existe e contém ao menos 2 partes separadas por "_"
              if valor and "_" in valor:
                  partes = valor.split("_")
                  if len(partes) >= 2:
                      penultima = partes[-2]  # penúltimo elemento
                      ultima = partes[-1]  # penúltimo elemento
                      del partes[-2]  # remove o penúltimo
                      fme_feature_type_origem = "_".join(partes)

                      feature.setAttribute("escala", penultima)
                      feature.setAttribute("geom_texto", ultima)
                      feature.setAttribute("fme_feature_type_origem", fme_feature_type_origem)
                  else:
                      feature.setAttribute("escala", "")
                      feature.setAttribute("geom_texto", "")
                      feature.setAttribute("fme_feature_type_origem", "")
              else:
                  feature.setAttribute("escala", "")
                  feature.setAttribute("geom_texto", "")
                  feature.setAttribute("fme_feature_type_origem", "")

              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> AttributeFilter_2
AttributeFilter_2
    ATTR_NAME = geom_texto
    ATTR_VALUES = <Empty>,<Missing>,<Null>,<Unfiltered>,a,l,p
    a -> Reprojector_4
    l -> Reprojector_2
    p -> Reprojector_3
Reprojector_4
    DEST = $(EPSG)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> TestFilter
TestFilter
    DEFAULT_VALUE = <UNFILTERED>
    PASSED_TEST_GROUP_OUTPUT = FIRST
    TEST_LIST = "BOOL_OP,OR,COMPOSITE_TEST,""""""1"""""",TEST_CLAUSE,TEST $(generelizar_para_ESCALA) = 50",50.000,"BOOL_OP,OR,COMPOSITE_TEST,""""""1"""""",TEST_CLAUSE,TEST $(generelizar_para_ESCALA) = 100",100.000,"BOOL_OP,OR,COMPOSITE_TEST,""""""1"""""",TEST_CLAUSE,TEST $(generelizar_para_ESCALA) = 250",250.000
    100.000 -> area_minima_valor_100K
    250.000 -> area_minima_valor_250K
area_minima_valor_100K: AttributeCreator
    ATTR_TABLE:
      SET_TO area_minima_valor (varchar(200)) = FME_CONDITIONAL:DEFAULT_VALUE'_FME_NO_OP_'BOOL_OP;OR;COMPOSITE_TEST;1;TEST @Value(fme_feature_type_origem) = edgv.cobter_area_edificada'250000'BOOL_OP;OR;COMPOSITE_TEST;1;TEST @Value(fme_feature_type_origem) = edgv.cobter_massa_dagua_a'40000'BOOL_OP;OR;COMPOSITE_TEST;1;TEST @Value(fme_feature_type_origem) = edgv.cobter_vegetacao_a'250000'BOOL_OP;OR;COMPOSITE_TEST;1;TEST @Value(fme_feature_type_origem) = edgv.constr_area_uso_especifico_a'1000000'BOOL_OP;OR;COMPOSITE_TEST;1;TEST @Value(fme_feature_type_origem) = edgv.constr_deposito_a'10000'BOOL_OP;OR;COMPOSITE_TEST;1;TEST @Value(fme_feature_type_origem) = edgv.constr_edificacao_a'10000'BOOL_OP;OR;COMPOSITE_TEST;1;TEST @Value(fme_feature_type_origem) = edgv.constr_extracao_mineral_a'10000'BOOL_OP;AND;COMPOSITE_TEST;1 AND 2;TEST @Value(fme_feature_type_origem) = edgv.constr_ocupacao_solo_a;TEST @Value(tipo_code) = 201'10000'BOOL_OP;AND;COMPOSITE_TEST;1 AND 2;TEST @Value(fme_feature_type_origem) = edgv.constr_ocupacao_solo_a;TEST @Value(tipo_code) = 104'40000'BOOL_OP;OR;COMPOSITE_TEST;1;TEST @Value(fme_feature_type_origem) = edgv.elemnat_elemento_hidrografico_a'40000'BOOL_OP;OR;COMPOSITE_TEST;1;TEST @Value(fme_feature_type_origem) = edgv.elemnat_ilha_a'40000'BOOL_OP;OR;COMPOSITE_TEST;1;TEST @Value(fme_feature_type_origem) = edgv.elemnat_terreno_sujeito_inundacao_a'40000'BOOL_OP;OR;COMPOSITE_TEST;1;TEST @Value(fme_feature_type_origem) = edgv.infra_pista_pouso_a'10000'FME_NUM_CONDITIONS14___
      SET_TO area (varchar(200)) = @Area()
    -> AttributeFilter
area_minima_valor_250K: AttributeCreator
    ATTR_TABLE:
      SET_TO area_minima_valor (varchar(200)) = FME_CONDITIONAL:DEFAULT_VALUE'_FME_NO_OP_'BOOL_OP;OR;COMPOSITE_TEST;1;TEST @Value(fme_feature_type_origem) = edgv.cobter_area_edificada'1562500'BOOL_OP;OR;COMPOSITE_TEST;1;TEST @Value(fme_feature_type_origem) = edgv.cobter_massa_dagua_a'100000'BOOL_OP;OR;COMPOSITE_TEST;1;TEST @Value(fme_feature_type_origem) = edgv.cobter_vegetacao_a'1562500'BOOL_OP;OR;COMPOSITE_TEST;1;TEST @Value(fme_feature_type_origem) = edgv.constr_area_uso_especifico_a'1000000'BOOL_OP;OR;COMPOSITE_TEST;1;TEST @Value(fme_feature_type_origem) = edgv.constr_deposito_a'62500'BOOL_OP;OR;COMPOSITE_TEST;1;TEST @Value(fme_feature_type_origem) = edgv.constr_edificacao_a'62500'BOOL_OP;OR;COMPOSITE_TEST;1;TEST @Value(fme_feature_type_origem) = edgv.constr_extracao_mineral_a'0'BOOL_OP;AND;COMPOSITE_TEST;1 AND 2;TEST @Value(fme_feature_type_origem) = edgv.constr_ocupacao_solo_a;TEST @Value(tipo_code) = 104'250000'BOOL_OP;OR;COMPOSITE_TEST;1;TEST @Value(fme_feature_type_origem) = edgv.elemnat_elemento_hidrografico_a'100000'BOOL_OP;OR;COMPOSITE_TEST;1;TEST @Value(fme_feature_type_origem) = edgv.elemnat_ilha_a'100000'BOOL_OP;OR;COMPOSITE_TEST;1;TEST @Value(fme_feature_type_origem) = edgv.elemnat_terreno_sujeito_inundacao_a'100000'BOOL_OP;OR;COMPOSITE_TEST;1;TEST @Value(fme_feature_type_origem) = edgv.infra_pista_pouso_a'62500'FME_NUM_CONDITIONS13___
      SET_TO area (varchar(200)) = @Area()
    -> AttributeFilter
AttributeFilter
    ATTR_NAME = fme_feature_type_origem
    ATTR_VALUES = <Empty>,<Missing>,<Null>,<Unfiltered>,edgv.aux_moldura_a,edgv.constr_area_uso_especifico_a,edgv.infra_pista_pouso_a,edgv.elemnat_ilha_a,edgv.elemnat_elemento_hidrografico_a,edgv.constr_ocupacao_solo_a,edgv.constr_extracao_mineral_a,edgv.constr_edificacao_a,edgv.constr_deposito_a,edgv.infra_barragem_a,edgv.cobter_massa_dagua_a,edgv.cobter_area_edificada_a,edgv.cobter_vegetacao_a,edgv.elemnat_terreno_sujeito_inundacao_a
    edgv.aux_moldura_a -> Junction_7
    edgv.constr_area_uso_especifico_a -> Junction_2
    edgv.infra_pista_pouso_a -> Junction_2
    edgv.elemnat_ilha_a -> Junction_2
    edgv.elemnat_elemento_hidrografico_a -> Junction_2
    edgv.constr_ocupacao_solo_a -> Junction_2
    edgv.constr_extracao_mineral_a -> Junction_2
    edgv.constr_edificacao_a -> Junction_2
    edgv.constr_deposito_a -> Junction_2
    edgv.infra_barragem_a -> Junction_6
    edgv.cobter_massa_dagua_a -> Generalizar_area_3 [Dissolver_Input]
    edgv.cobter_area_edificada_a -> Generalizar_area_2 [Dissolver_Input]
    edgv.cobter_vegetacao_a -> Generalizar_area [Dissolver_Input]
    edgv.elemnat_terreno_sujeito_inundacao_a -> Generalizar_area_5 [Dissolver_Input]
Junction_2
    -> Tester_2
Tester_2
    BOOL_OP = OR
    TEST_CLAUSE = TEST @Value(area) >= @Value(area_minima_valor)
    TEST_MODE = TEST
    PASSED -> Junction_6
Junction_6
    -> Outros
    -> Junction_5
Outros: Inspector [off]
    TACKATTRS = fme_feature_type_origem
Generalizar_area_3
    ADMINISTRACAO_CODE = @Value(administracao_code)
    ADMINISTRACAO_VALUE = @Value(administracao_value)
    ALTITUDE = @Value(altitude)
    ALTITUDE_GEOMETRICA = @Value(altitude_geometrica)
    ALTITUDE_ORTOMETRICA = @Value(altitude_ortometrica)
    ALTURA = @Value(altura)
    ANCORA_HORIZONTAL_CODE = @Value(ancora_horizontal_code)
    ANCORA_HORIZONTAL_VALUE = @Value(ancora_horizontal_value)
    ANCORA_VERTICAL_CODE = @Value(ancora_vertical_code)
    ANCORA_VERTICAL_VALUE = @Value(ancora_vertical_value)
    AREA_MINIMA_VALOR = @Value(area_minima_valor)
    ASSENTAMENTO_PRECARIO_CODE = @Value(assentamento_precario_code)
    ASSENTAMENTO_PRECARIO_VALUE = @Value(assentamento_precario_value)
    BITOLA_CODE = @Value(bitola_code)
    BITOLA_VALUE = @Value(bitola_value)
    CANTEIRO_DIVISORIO_CODE = @Value(canteiro_divisorio_code)
    CANTEIRO_DIVISORIO_VALUE = @Value(canteiro_divisorio_value)
    COD_PONTO = @Value(cod_ponto)
    CONCESSIONARIA = @Value(concessionaria)
    CONFIG_COMPRIMENTO_SIMB_CODE = @Value(config_comprimento_simb_code)
    CONFIG_COMPRIMENTO_SIMB_VALUE = @Value(config_comprimento_simb_value)
    COR = @Value(cor)
    CORRIGIDO_CODE = @Value(corrigido_code)
    CORRIGIDO_VALUE = @Value(corrigido_value)
    COTA = @Value(cota)
    COTA_COMPROVADA_CODE = @Value(cota_comprovada_code)
    COTA_COMPROVADA_VALUE = @Value(cota_comprovada_value)
    COTA_MAIS_ALTA_CODE = @Value(cota_mais_alta_code)
    COTA_MAIS_ALTA_VALUE = @Value(cota_mais_alta_value)
    DENTRO_MASSA_DAGUA_CODE = @Value(dentro_massa_dagua_code)
    DENTRO_MASSA_DAGUA_VALUE = @Value(dentro_massa_dagua_value)
    DEPRESSAO_CODE = @Value(depressao_code)
    DEPRESSAO_VALUE = @Value(depressao_value)
    DESCRICAO = @Value(descricao)
    DESLOC = @Value(desloc)
    DIRECAO = @Value(direcao)
    DIRECAO_FIXADA_CODE = @Value(direcao_fixada_code)
    DIRECAO_FIXADA_VALUE = @Value(direcao_fixada_value)
    ELETRIFICADA_CODE = @Value(eletrificada_code)
    ELETRIFICADA_VALUE = @Value(eletrificada_value)
    EM_ARRUAMENTO_CODE = @Value(em_arruamento_code)
    EM_ARRUAMENTO_VALUE = @Value(em_arruamento_value)
    EM_GALERIA_BUEIRO_CODE = @Value(em_galeria_bueiro_code)
    EM_GALERIA_BUEIRO_VALUE = @Value(em_galeria_bueiro_value)
    ESCALA = @Value(escala)
    ESPACAMENTO = @Value(espacamento)
    ESTILO_FONTE = @Value(estilo_fonte)
    EXIBIR_LADO_SIMBOLOGIA_CODE = @Value(exibir_lado_simbologia_code)
    EXIBIR_LADO_SIMBOLOGIA_VALUE = @Value(exibir_lado_simbologia_value)
    EXIBIR_LINHA_ROTULO_CODE = @Value(exibir_linha_rotulo_code)
    EXIBIR_LINHA_ROTULO_VALUE = @Value(exibir_linha_rotulo_value)
    EXIBIR_PONTA_SIMBOLOGIA_CODE = @Value(exibir_ponta_simbologia_code)
    EXIBIR_PONTA_SIMBOLOGIA_VALUE = @Value(exibir_ponta_simbologia_value)
    EXIBIR_ROTULO_APROXIMADO_CODE = @Value(exibir_rotulo_aproximado_code)
    EXIBIR_ROTULO_APROXIMADO_VALUE = @Value(exibir_rotulo_aproximado_value)
    FINALIDADE_CODE = @Value(finalidade_code)
    FINALIDADE_VALUE = @Value(finalidade_value)
    FME_FEATURE_TYPE = @Value(fme_feature_type)
    FME_FEATURE_TYPE_ORIGEM = @Value(fme_feature_type_origem)
    FORMA_EXTRACAO_CODE = @Value(forma_extracao_code)
    FORMA_EXTRACAO_VALUE = @Value(forma_extracao_value)
    GEOMETRIA_APROXIMADA_CODE = @Value(geometria_aproximada_code)
    GEOMETRIA_APROXIMADA_VALUE = @Value(geometria_aproximada_value)
    GEOM_TEXTO = @Value(geom_texto)
    ID = @Value(id)
    INDICE_CODE = @Value(indice_code)
    INDICE_VALUE = @Value(indice_value)
    INOM = @Value(inom)
    JURISDICAO_CODE = @Value(jurisdicao_code)
    JURISDICAO_VALUE = @Value(jurisdicao_value)
    JUSTIFICATIVA = @Value(justificativa)
    JUSTIFICATIVA_TXT_CODE = @Value(justificativa_txt_code)
    JUSTIFICATIVA_TXT_VALUE = @Value(justificativa_txt_value)
    LABEL_X = @Value(label_x)
    LABEL_Y = @Value(label_y)
    LARGURA_SIMBOLOGIA = @Value(largura_simbologia)
    LATITUDE = @Value(latitude)
    LONGITUDE = @Value(longitude)
    MATERIAL_CONSTRUCAO_CODE = @Value(material_construcao_code)
    MATERIAL_CONSTRUCAO_ELEMENTO_VIARIO_CODE = @Value(material_construcao_elemento_viario_code)
    MATERIAL_CONSTRUCAO_ELEMENTO_VIARIO_VALUE = @Value(material_construcao_elemento_viario_value)
    MATERIAL_CONSTRUCAO_VALUE = @Value(material_construcao_value)
    MI = @Value(mi)
    MODAL_USO_CODE = @Value(modal_uso_code)
    MODAL_USO_VALUE = @Value(modal_uso_value)
    NOME = @Value(nome)
    NOME_ELEMENTO_VIARIO = @Value(nome_elemento_viario)
    NR_FAIXAS = @Value(nr_faixas)
    NR_LINHAS_CODE = @Value(nr_linhas_code)
    NR_LINHAS_VALUE = @Value(nr_linhas_value)
    NR_PISTAS = @Value(nr_pistas)
    NUMERO = @Value(numero)
    OBSERVACAO = @Value(observacao)
    ORDEM_SIMBOLOGIA = @Value(ordem_simbologia)
    ORGAO_RESPONSAVEL = @Value(orgao_responsavel)
    POPULACAO = @Value(populacao)
    POSICAO_PISTA_CODE = @Value(posicao_pista_code)
    POSICAO_PISTA_ELEMENTO_VIARIO_CODE = @Value(posicao_pista_elemento_viario_code)
    POSICAO_PISTA_ELEMENTO_VIARIO_VALUE = @Value(posicao_pista_elemento_viario_value)
    POSICAO_PISTA_VALUE = @Value(posicao_pista_value)
    POSICAO_RELATIVA_CODE = @Value(posicao_relativa_code)
    POSICAO_RELATIVA_VALUE = @Value(posicao_relativa_value)
    POSICAO_ROTULO_CODE = @Value(posicao_rotulo_code)
    POSICAO_ROTULO_VALUE = @Value(posicao_rotulo_value)
    REFERENCIAL_ALTIM_CODE = @Value(referencial_altim_code)
    REFERENCIAL_ALTIM_VALUE = @Value(referencial_altim_value)
    REFERENCIAL_GRAV_CODE = @Value(referencial_grav_code)
    REFERENCIAL_GRAV_VALUE = @Value(referencial_grav_value)
    REGIME_CODE = @Value(regime_code)
    REGIME_VALUE = @Value(regime_value)
    REVESTIMENTO_CODE = @Value(revestimento_code)
    REVESTIMENTO_VALUE = @Value(revestimento_value)
    SIGLA = @Value(sigla)
    SIGLA_CODE = @Value(sigla_code)
    SIGLA_VALUE = @Value(sigla_value)
    SIMB_ROT = @Value(simb_rot)
    SISTEMA_GEODESICO_CODE = @Value(sistema_geodesico_code)
    SISTEMA_GEODESICO_VALUE = @Value(sistema_geodesico_value)
    SITUACAO_EM_POLIGONO_CODE = @Value(situacao_em_poligono_code)
    SITUACAO_EM_POLIGONO_VALUE = @Value(situacao_em_poligono_value)
    SITUACAO_FISICA_CODE = @Value(situacao_fisica_code)
    SITUACAO_FISICA_VALUE = @Value(situacao_fisica_value)
    SITUACAO_MARCO_CODE = @Value(situacao_marco_code)
    SITUACAO_MARCO_VALUE = @Value(situacao_marco_value)
    SOBREPOSTO_CODE = @Value(sobreposto_code)
    SOBREPOSTO_TRANSPORTES_CODE = @Value(sobreposto_transportes_code)
    SOBREPOSTO_TRANSPORTES_VALUE = @Value(sobreposto_transportes_value)
    SOBREPOSTO_VALUE = @Value(sobreposto_value)
    SUBFASE_ID = @Value(subfase_id)
    SUJEITO_INUNDACAO_CODE = @Value(sujeito_inundacao_code)
    SUJEITO_INUNDACAO_VALUE = @Value(sujeito_inundacao_value)
    SUPRIMIR_BANDEIRA_CODE = @Value(suprimir_bandeira_code)
    SUPRIMIR_BANDEIRA_VALUE = @Value(suprimir_bandeira_value)
    SUPRIMIR_SIMBOLOGIA_CODE = @Value(suprimir_simbologia_code)
    SUPRIMIR_SIMBOLOGIA_VALUE = @Value(suprimir_simbologia_value)
    TAMANHO_TXT = @Value(tamanho_txt)
    TEXTO_EDICAO = @Value(texto_edicao)
    TIPO_CODE = @Value(tipo_code)
    TIPO_ELEMENTO_VIARIO_CODE = @Value(tipo_elemento_viario_code)
    TIPO_ELEMENTO_VIARIO_VALUE = @Value(tipo_elemento_viario_value)
    TIPO_EXPOSICAO_CODE = @Value(tipo_exposicao_code)
    TIPO_EXPOSICAO_VALUE = @Value(tipo_exposicao_value)
    TIPO_GRID = @Value(tipo_grid)
    TIPO_PRODUTO_CODE = @Value(tipo_produto_code)
    TIPO_PRODUTO_VALUE = @Value(tipo_produto_value)
    TIPO_REF_CODE = @Value(tipo_ref_code)
    TIPO_REF_VALUE = @Value(tipo_ref_value)
    TIPO_VALUE = @Value(tipo_value)
    TRAFEGO_CODE = @Value(trafego_code)
    TRAFEGO_VALUE = @Value(trafego_value)
    USO_PISTA_CODE = @Value(uso_pista_code)
    USO_PISTA_VALUE = @Value(uso_pista_value)
    VEG_MIN_100K = 250000
    VISIVEL_CODE = @Value(visivel_code)
    VISIVEL_VALUE = @Value(visivel_value)
    FeatureMerger_Merged -> Generalizar_area_4 [Dissolver_Input]
    NeighborFinder_UnmatchedBase -> Generalizar_area_4 [Dissolver_Input]
Generalizar_area_2
    ADMINISTRACAO_CODE = @Value(administracao_code)
    ADMINISTRACAO_VALUE = @Value(administracao_value)
    ALTITUDE = @Value(altitude)
    ALTITUDE_GEOMETRICA = @Value(altitude_geometrica)
    ALTITUDE_ORTOMETRICA = @Value(altitude_ortometrica)
    ALTURA = @Value(altura)
    ANCORA_HORIZONTAL_CODE = @Value(ancora_horizontal_code)
    ANCORA_HORIZONTAL_VALUE = @Value(ancora_horizontal_value)
    ANCORA_VERTICAL_CODE = @Value(ancora_vertical_code)
    ANCORA_VERTICAL_VALUE = @Value(ancora_vertical_value)
    AREA_MINIMA_VALOR = @Value(area_minima_valor)
    ASSENTAMENTO_PRECARIO_CODE = @Value(assentamento_precario_code)
    ASSENTAMENTO_PRECARIO_VALUE = @Value(assentamento_precario_value)
    BITOLA_CODE = @Value(bitola_code)
    BITOLA_VALUE = @Value(bitola_value)
    CANTEIRO_DIVISORIO_CODE = @Value(canteiro_divisorio_code)
    CANTEIRO_DIVISORIO_VALUE = @Value(canteiro_divisorio_value)
    COD_PONTO = @Value(cod_ponto)
    CONCESSIONARIA = @Value(concessionaria)
    CONFIG_COMPRIMENTO_SIMB_CODE = @Value(config_comprimento_simb_code)
    CONFIG_COMPRIMENTO_SIMB_VALUE = @Value(config_comprimento_simb_value)
    COR = @Value(cor)
    CORRIGIDO_CODE = @Value(corrigido_code)
    CORRIGIDO_VALUE = @Value(corrigido_value)
    COTA = @Value(cota)
    COTA_COMPROVADA_CODE = @Value(cota_comprovada_code)
    COTA_COMPROVADA_VALUE = @Value(cota_comprovada_value)
    COTA_MAIS_ALTA_CODE = @Value(cota_mais_alta_code)
    COTA_MAIS_ALTA_VALUE = @Value(cota_mais_alta_value)
    DENTRO_MASSA_DAGUA_CODE = @Value(dentro_massa_dagua_code)
    DENTRO_MASSA_DAGUA_VALUE = @Value(dentro_massa_dagua_value)
    DEPRESSAO_CODE = @Value(depressao_code)
    DEPRESSAO_VALUE = @Value(depressao_value)
    DESCRICAO = @Value(descricao)
    DESLOC = @Value(desloc)
    DIRECAO = @Value(direcao)
    DIRECAO_FIXADA_CODE = @Value(direcao_fixada_code)
    DIRECAO_FIXADA_VALUE = @Value(direcao_fixada_value)
    ELETRIFICADA_CODE = @Value(eletrificada_code)
    ELETRIFICADA_VALUE = @Value(eletrificada_value)
    EM_ARRUAMENTO_CODE = @Value(em_arruamento_code)
    EM_ARRUAMENTO_VALUE = @Value(em_arruamento_value)
    EM_GALERIA_BUEIRO_CODE = @Value(em_galeria_bueiro_code)
    EM_GALERIA_BUEIRO_VALUE = @Value(em_galeria_bueiro_value)
    ESCALA = @Value(escala)
    ESPACAMENTO = @Value(espacamento)
    ESTILO_FONTE = @Value(estilo_fonte)
    EXIBIR_LADO_SIMBOLOGIA_CODE = @Value(exibir_lado_simbologia_code)
    EXIBIR_LADO_SIMBOLOGIA_VALUE = @Value(exibir_lado_simbologia_value)
    EXIBIR_LINHA_ROTULO_CODE = @Value(exibir_linha_rotulo_code)
    EXIBIR_LINHA_ROTULO_VALUE = @Value(exibir_linha_rotulo_value)
    EXIBIR_PONTA_SIMBOLOGIA_CODE = @Value(exibir_ponta_simbologia_code)
    EXIBIR_PONTA_SIMBOLOGIA_VALUE = @Value(exibir_ponta_simbologia_value)
    EXIBIR_ROTULO_APROXIMADO_CODE = @Value(exibir_rotulo_aproximado_code)
    EXIBIR_ROTULO_APROXIMADO_VALUE = @Value(exibir_rotulo_aproximado_value)
    FINALIDADE_CODE = @Value(finalidade_code)
    FINALIDADE_VALUE = @Value(finalidade_value)
    FME_FEATURE_TYPE = @Value(fme_feature_type)
    FME_FEATURE_TYPE_ORIGEM = @Value(fme_feature_type_origem)
    FORMA_EXTRACAO_CODE = @Value(forma_extracao_code)
    FORMA_EXTRACAO_VALUE = @Value(forma_extracao_value)
    GEOMETRIA_APROXIMADA_CODE = @Value(geometria_aproximada_code)
    GEOMETRIA_APROXIMADA_VALUE = @Value(geometria_aproximada_value)
    GEOM_TEXTO = @Value(geom_texto)
    ID = @Value(id)
    INDICE_CODE = @Value(indice_code)
    INDICE_VALUE = @Value(indice_value)
    INOM = @Value(inom)
    JURISDICAO_CODE = @Value(jurisdicao_code)
    JURISDICAO_VALUE = @Value(jurisdicao_value)
    JUSTIFICATIVA = @Value(justificativa)
    JUSTIFICATIVA_TXT_CODE = @Value(justificativa_txt_code)
    JUSTIFICATIVA_TXT_VALUE = @Value(justificativa_txt_value)
    LABEL_X = @Value(label_x)
    LABEL_Y = @Value(label_y)
    LARGURA_SIMBOLOGIA = @Value(largura_simbologia)
    LATITUDE = @Value(latitude)
    LONGITUDE = @Value(longitude)
    MATERIAL_CONSTRUCAO_CODE = @Value(material_construcao_code)
    MATERIAL_CONSTRUCAO_ELEMENTO_VIARIO_CODE = @Value(material_construcao_elemento_viario_code)
    MATERIAL_CONSTRUCAO_ELEMENTO_VIARIO_VALUE = @Value(material_construcao_elemento_viario_value)
    MATERIAL_CONSTRUCAO_VALUE = @Value(material_construcao_value)
    MI = @Value(mi)
    MODAL_USO_CODE = @Value(modal_uso_code)
    MODAL_USO_VALUE = @Value(modal_uso_value)
    NOME = @Value(nome)
    NOME_ELEMENTO_VIARIO = @Value(nome_elemento_viario)
    NR_FAIXAS = @Value(nr_faixas)
    NR_LINHAS_CODE = @Value(nr_linhas_code)
    NR_LINHAS_VALUE = @Value(nr_linhas_value)
    NR_PISTAS = @Value(nr_pistas)
    NUMERO = @Value(numero)
    OBSERVACAO = @Value(observacao)
    ORDEM_SIMBOLOGIA = @Value(ordem_simbologia)
    ORGAO_RESPONSAVEL = @Value(orgao_responsavel)
    POPULACAO = @Value(populacao)
    POSICAO_PISTA_CODE = @Value(posicao_pista_code)
    POSICAO_PISTA_ELEMENTO_VIARIO_CODE = @Value(posicao_pista_elemento_viario_code)
    POSICAO_PISTA_ELEMENTO_VIARIO_VALUE = @Value(posicao_pista_elemento_viario_value)
    POSICAO_PISTA_VALUE = @Value(posicao_pista_value)
    POSICAO_RELATIVA_CODE = @Value(posicao_relativa_code)
    POSICAO_RELATIVA_VALUE = @Value(posicao_relativa_value)
    POSICAO_ROTULO_CODE = @Value(posicao_rotulo_code)
    POSICAO_ROTULO_VALUE = @Value(posicao_rotulo_value)
    REFERENCIAL_ALTIM_CODE = @Value(referencial_altim_code)
    REFERENCIAL_ALTIM_VALUE = @Value(referencial_altim_value)
    REFERENCIAL_GRAV_CODE = @Value(referencial_grav_code)
    REFERENCIAL_GRAV_VALUE = @Value(referencial_grav_value)
    REGIME_CODE = @Value(regime_code)
    REGIME_VALUE = @Value(regime_value)
    REVESTIMENTO_CODE = @Value(revestimento_code)
    REVESTIMENTO_VALUE = @Value(revestimento_value)
    SIGLA = @Value(sigla)
    SIGLA_CODE = @Value(sigla_code)
    SIGLA_VALUE = @Value(sigla_value)
    SIMB_ROT = @Value(simb_rot)
    SISTEMA_GEODESICO_CODE = @Value(sistema_geodesico_code)
    SISTEMA_GEODESICO_VALUE = @Value(sistema_geodesico_value)
    SITUACAO_EM_POLIGONO_CODE = @Value(situacao_em_poligono_code)
    SITUACAO_EM_POLIGONO_VALUE = @Value(situacao_em_poligono_value)
    SITUACAO_FISICA_CODE = @Value(situacao_fisica_code)
    SITUACAO_FISICA_VALUE = @Value(situacao_fisica_value)
    SITUACAO_MARCO_CODE = @Value(situacao_marco_code)
    SITUACAO_MARCO_VALUE = @Value(situacao_marco_value)
    SOBREPOSTO_CODE = @Value(sobreposto_code)
    SOBREPOSTO_TRANSPORTES_CODE = @Value(sobreposto_transportes_code)
    SOBREPOSTO_TRANSPORTES_VALUE = @Value(sobreposto_transportes_value)
    SOBREPOSTO_VALUE = @Value(sobreposto_value)
    SUBFASE_ID = @Value(subfase_id)
    SUJEITO_INUNDACAO_CODE = @Value(sujeito_inundacao_code)
    SUJEITO_INUNDACAO_VALUE = @Value(sujeito_inundacao_value)
    SUPRIMIR_BANDEIRA_CODE = @Value(suprimir_bandeira_code)
    SUPRIMIR_BANDEIRA_VALUE = @Value(suprimir_bandeira_value)
    SUPRIMIR_SIMBOLOGIA_CODE = @Value(suprimir_simbologia_code)
    SUPRIMIR_SIMBOLOGIA_VALUE = @Value(suprimir_simbologia_value)
    TAMANHO_TXT = @Value(tamanho_txt)
    TEXTO_EDICAO = @Value(texto_edicao)
    TIPO_CODE = @Value(tipo_code)
    TIPO_ELEMENTO_VIARIO_CODE = @Value(tipo_elemento_viario_code)
    TIPO_ELEMENTO_VIARIO_VALUE = @Value(tipo_elemento_viario_value)
    TIPO_EXPOSICAO_CODE = @Value(tipo_exposicao_code)
    TIPO_EXPOSICAO_VALUE = @Value(tipo_exposicao_value)
    TIPO_GRID = @Value(tipo_grid)
    TIPO_PRODUTO_CODE = @Value(tipo_produto_code)
    TIPO_PRODUTO_VALUE = @Value(tipo_produto_value)
    TIPO_REF_CODE = @Value(tipo_ref_code)
    TIPO_REF_VALUE = @Value(tipo_ref_value)
    TIPO_VALUE = @Value(tipo_value)
    TRAFEGO_CODE = @Value(trafego_code)
    TRAFEGO_VALUE = @Value(trafego_value)
    USO_PISTA_CODE = @Value(uso_pista_code)
    USO_PISTA_VALUE = @Value(uso_pista_value)
    VEG_MIN_100K = 250000
    VISIVEL_CODE = @Value(visivel_code)
    VISIVEL_VALUE = @Value(visivel_value)
    FeatureMerger_Merged -> Generalizar_area_4 [Dissolver_Input]
    NeighborFinder_UnmatchedBase -> Generalizar_area_4 [Dissolver_Input]
Generalizar_area
    ADMINISTRACAO_CODE = @Value(administracao_code)
    ADMINISTRACAO_VALUE = @Value(administracao_value)
    ALTITUDE = @Value(altitude)
    ALTITUDE_GEOMETRICA = @Value(altitude_geometrica)
    ALTITUDE_ORTOMETRICA = @Value(altitude_ortometrica)
    ALTURA = @Value(altura)
    ANCORA_HORIZONTAL_CODE = @Value(ancora_horizontal_code)
    ANCORA_HORIZONTAL_VALUE = @Value(ancora_horizontal_value)
    ANCORA_VERTICAL_CODE = @Value(ancora_vertical_code)
    ANCORA_VERTICAL_VALUE = @Value(ancora_vertical_value)
    AREA_MINIMA_VALOR = @Value(area_minima_valor)
    ASSENTAMENTO_PRECARIO_CODE = @Value(assentamento_precario_code)
    ASSENTAMENTO_PRECARIO_VALUE = @Value(assentamento_precario_value)
    BITOLA_CODE = @Value(bitola_code)
    BITOLA_VALUE = @Value(bitola_value)
    CANTEIRO_DIVISORIO_CODE = @Value(canteiro_divisorio_code)
    CANTEIRO_DIVISORIO_VALUE = @Value(canteiro_divisorio_value)
    COD_PONTO = @Value(cod_ponto)
    CONCESSIONARIA = @Value(concessionaria)
    CONFIG_COMPRIMENTO_SIMB_CODE = @Value(config_comprimento_simb_code)
    CONFIG_COMPRIMENTO_SIMB_VALUE = @Value(config_comprimento_simb_value)
    COR = @Value(cor)
    CORRIGIDO_CODE = @Value(corrigido_code)
    CORRIGIDO_VALUE = @Value(corrigido_value)
    COTA = @Value(cota)
    COTA_COMPROVADA_CODE = @Value(cota_comprovada_code)
    COTA_COMPROVADA_VALUE = @Value(cota_comprovada_value)
    COTA_MAIS_ALTA_CODE = @Value(cota_mais_alta_code)
    COTA_MAIS_ALTA_VALUE = @Value(cota_mais_alta_value)
    DENTRO_MASSA_DAGUA_CODE = @Value(dentro_massa_dagua_code)
    DENTRO_MASSA_DAGUA_VALUE = @Value(dentro_massa_dagua_value)
    DEPRESSAO_CODE = @Value(depressao_code)
    DEPRESSAO_VALUE = @Value(depressao_value)
    DESCRICAO = @Value(descricao)
    DESLOC = @Value(desloc)
    DIRECAO = @Value(direcao)
    DIRECAO_FIXADA_CODE = @Value(direcao_fixada_code)
    DIRECAO_FIXADA_VALUE = @Value(direcao_fixada_value)
    ELETRIFICADA_CODE = @Value(eletrificada_code)
    ELETRIFICADA_VALUE = @Value(eletrificada_value)
    EM_ARRUAMENTO_CODE = @Value(em_arruamento_code)
    EM_ARRUAMENTO_VALUE = @Value(em_arruamento_value)
    EM_GALERIA_BUEIRO_CODE = @Value(em_galeria_bueiro_code)
    EM_GALERIA_BUEIRO_VALUE = @Value(em_galeria_bueiro_value)
    ESCALA = @Value(escala)
    ESPACAMENTO = @Value(espacamento)
    ESTILO_FONTE = @Value(estilo_fonte)
    EXIBIR_LADO_SIMBOLOGIA_CODE = @Value(exibir_lado_simbologia_code)
    EXIBIR_LADO_SIMBOLOGIA_VALUE = @Value(exibir_lado_simbologia_value)
    EXIBIR_LINHA_ROTULO_CODE = @Value(exibir_linha_rotulo_code)
    EXIBIR_LINHA_ROTULO_VALUE = @Value(exibir_linha_rotulo_value)
    EXIBIR_PONTA_SIMBOLOGIA_CODE = @Value(exibir_ponta_simbologia_code)
    EXIBIR_PONTA_SIMBOLOGIA_VALUE = @Value(exibir_ponta_simbologia_value)
    EXIBIR_ROTULO_APROXIMADO_CODE = @Value(exibir_rotulo_aproximado_code)
    EXIBIR_ROTULO_APROXIMADO_VALUE = @Value(exibir_rotulo_aproximado_value)
    FINALIDADE_CODE = @Value(finalidade_code)
    FINALIDADE_VALUE = @Value(finalidade_value)
    FME_FEATURE_TYPE = @Value(fme_feature_type)
    FME_FEATURE_TYPE_ORIGEM = @Value(fme_feature_type_origem)
    FORMA_EXTRACAO_CODE = @Value(forma_extracao_code)
    FORMA_EXTRACAO_VALUE = @Value(forma_extracao_value)
    GEOMETRIA_APROXIMADA_CODE = @Value(geometria_aproximada_code)
    GEOMETRIA_APROXIMADA_VALUE = @Value(geometria_aproximada_value)
    GEOM_TEXTO = @Value(geom_texto)
    ID = @Value(id)
    INDICE_CODE = @Value(indice_code)
    INDICE_VALUE = @Value(indice_value)
    INOM = @Value(inom)
    JURISDICAO_CODE = @Value(jurisdicao_code)
    JURISDICAO_VALUE = @Value(jurisdicao_value)
    JUSTIFICATIVA = @Value(justificativa)
    JUSTIFICATIVA_TXT_CODE = @Value(justificativa_txt_code)
    JUSTIFICATIVA_TXT_VALUE = @Value(justificativa_txt_value)
    LABEL_X = @Value(label_x)
    LABEL_Y = @Value(label_y)
    LARGURA_SIMBOLOGIA = @Value(largura_simbologia)
    LATITUDE = @Value(latitude)
    LONGITUDE = @Value(longitude)
    MATERIAL_CONSTRUCAO_CODE = @Value(material_construcao_code)
    MATERIAL_CONSTRUCAO_ELEMENTO_VIARIO_CODE = @Value(material_construcao_elemento_viario_code)
    MATERIAL_CONSTRUCAO_ELEMENTO_VIARIO_VALUE = @Value(material_construcao_elemento_viario_value)
    MATERIAL_CONSTRUCAO_VALUE = @Value(material_construcao_value)
    MI = @Value(mi)
    MODAL_USO_CODE = @Value(modal_uso_code)
    MODAL_USO_VALUE = @Value(modal_uso_value)
    NOME = @Value(nome)
    NOME_ELEMENTO_VIARIO = @Value(nome_elemento_viario)
    NR_FAIXAS = @Value(nr_faixas)
    NR_LINHAS_CODE = @Value(nr_linhas_code)
    NR_LINHAS_VALUE = @Value(nr_linhas_value)
    NR_PISTAS = @Value(nr_pistas)
    NUMERO = @Value(numero)
    OBSERVACAO = @Value(observacao)
    ORDEM_SIMBOLOGIA = @Value(ordem_simbologia)
    ORGAO_RESPONSAVEL = @Value(orgao_responsavel)
    POPULACAO = @Value(populacao)
    POSICAO_PISTA_CODE = @Value(posicao_pista_code)
    POSICAO_PISTA_ELEMENTO_VIARIO_CODE = @Value(posicao_pista_elemento_viario_code)
    POSICAO_PISTA_ELEMENTO_VIARIO_VALUE = @Value(posicao_pista_elemento_viario_value)
    POSICAO_PISTA_VALUE = @Value(posicao_pista_value)
    POSICAO_RELATIVA_CODE = @Value(posicao_relativa_code)
    POSICAO_RELATIVA_VALUE = @Value(posicao_relativa_value)
    POSICAO_ROTULO_CODE = @Value(posicao_rotulo_code)
    POSICAO_ROTULO_VALUE = @Value(posicao_rotulo_value)
    REFERENCIAL_ALTIM_CODE = @Value(referencial_altim_code)
    REFERENCIAL_ALTIM_VALUE = @Value(referencial_altim_value)
    REFERENCIAL_GRAV_CODE = @Value(referencial_grav_code)
    REFERENCIAL_GRAV_VALUE = @Value(referencial_grav_value)
    REGIME_CODE = @Value(regime_code)
    REGIME_VALUE = @Value(regime_value)
    REVESTIMENTO_CODE = @Value(revestimento_code)
    REVESTIMENTO_VALUE = @Value(revestimento_value)
    SIGLA = @Value(sigla)
    SIGLA_CODE = @Value(sigla_code)
    SIGLA_VALUE = @Value(sigla_value)
    SIMB_ROT = @Value(simb_rot)
    SISTEMA_GEODESICO_CODE = @Value(sistema_geodesico_code)
    SISTEMA_GEODESICO_VALUE = @Value(sistema_geodesico_value)
    SITUACAO_EM_POLIGONO_CODE = @Value(situacao_em_poligono_code)
    SITUACAO_EM_POLIGONO_VALUE = @Value(situacao_em_poligono_value)
    SITUACAO_FISICA_CODE = @Value(situacao_fisica_code)
    SITUACAO_FISICA_VALUE = @Value(situacao_fisica_value)
    SITUACAO_MARCO_CODE = @Value(situacao_marco_code)
    SITUACAO_MARCO_VALUE = @Value(situacao_marco_value)
    SOBREPOSTO_CODE = @Value(sobreposto_code)
    SOBREPOSTO_TRANSPORTES_CODE = @Value(sobreposto_transportes_code)
    SOBREPOSTO_TRANSPORTES_VALUE = @Value(sobreposto_transportes_value)
    SOBREPOSTO_VALUE = @Value(sobreposto_value)
    SUBFASE_ID = @Value(subfase_id)
    SUJEITO_INUNDACAO_CODE = @Value(sujeito_inundacao_code)
    SUJEITO_INUNDACAO_VALUE = @Value(sujeito_inundacao_value)
    SUPRIMIR_BANDEIRA_CODE = @Value(suprimir_bandeira_code)
    SUPRIMIR_BANDEIRA_VALUE = @Value(suprimir_bandeira_value)
    SUPRIMIR_SIMBOLOGIA_CODE = @Value(suprimir_simbologia_code)
    SUPRIMIR_SIMBOLOGIA_VALUE = @Value(suprimir_simbologia_value)
    TAMANHO_TXT = @Value(tamanho_txt)
    TEXTO_EDICAO = @Value(texto_edicao)
    TIPO_CODE = @Value(tipo_code)
    TIPO_ELEMENTO_VIARIO_CODE = @Value(tipo_elemento_viario_code)
    TIPO_ELEMENTO_VIARIO_VALUE = @Value(tipo_elemento_viario_value)
    TIPO_EXPOSICAO_CODE = @Value(tipo_exposicao_code)
    TIPO_EXPOSICAO_VALUE = @Value(tipo_exposicao_value)
    TIPO_GRID = @Value(tipo_grid)
    TIPO_PRODUTO_CODE = @Value(tipo_produto_code)
    TIPO_PRODUTO_VALUE = @Value(tipo_produto_value)
    TIPO_REF_CODE = @Value(tipo_ref_code)
    TIPO_REF_VALUE = @Value(tipo_ref_value)
    TIPO_VALUE = @Value(tipo_value)
    TRAFEGO_CODE = @Value(trafego_code)
    TRAFEGO_VALUE = @Value(trafego_value)
    USO_PISTA_CODE = @Value(uso_pista_code)
    USO_PISTA_VALUE = @Value(uso_pista_value)
    VEG_MIN_100K = 250000
    VISIVEL_CODE = @Value(visivel_code)
    VISIVEL_VALUE = @Value(visivel_value)
    FeatureMerger_Merged -> Generalizar_area_4 [Dissolver_Input]
    NeighborFinder_UnmatchedBase -> Generalizar_area_4 [Dissolver_Input]
Generalizar_area_4
    ADMINISTRACAO_CODE = @Value(administracao_code)
    ADMINISTRACAO_VALUE = @Value(administracao_value)
    ALTITUDE = @Value(altitude)
    ALTITUDE_GEOMETRICA = @Value(altitude_geometrica)
    ALTITUDE_ORTOMETRICA = @Value(altitude_ortometrica)
    ALTURA = @Value(altura)
    ANCORA_HORIZONTAL_CODE = @Value(ancora_horizontal_code)
    ANCORA_HORIZONTAL_VALUE = @Value(ancora_horizontal_value)
    ANCORA_VERTICAL_CODE = @Value(ancora_vertical_code)
    ANCORA_VERTICAL_VALUE = @Value(ancora_vertical_value)
    AREA_MINIMA_VALOR = @Value(area_minima_valor)
    ASSENTAMENTO_PRECARIO_CODE = @Value(assentamento_precario_code)
    ASSENTAMENTO_PRECARIO_VALUE = @Value(assentamento_precario_value)
    BITOLA_CODE = @Value(bitola_code)
    BITOLA_VALUE = @Value(bitola_value)
    CANTEIRO_DIVISORIO_CODE = @Value(canteiro_divisorio_code)
    CANTEIRO_DIVISORIO_VALUE = @Value(canteiro_divisorio_value)
    COD_PONTO = @Value(cod_ponto)
    CONCESSIONARIA = @Value(concessionaria)
    CONFIG_COMPRIMENTO_SIMB_CODE = @Value(config_comprimento_simb_code)
    CONFIG_COMPRIMENTO_SIMB_VALUE = @Value(config_comprimento_simb_value)
    COR = @Value(cor)
    CORRIGIDO_CODE = @Value(corrigido_code)
    CORRIGIDO_VALUE = @Value(corrigido_value)
    COTA = @Value(cota)
    COTA_COMPROVADA_CODE = @Value(cota_comprovada_code)
    COTA_COMPROVADA_VALUE = @Value(cota_comprovada_value)
    COTA_MAIS_ALTA_CODE = @Value(cota_mais_alta_code)
    COTA_MAIS_ALTA_VALUE = @Value(cota_mais_alta_value)
    DENTRO_MASSA_DAGUA_CODE = @Value(dentro_massa_dagua_code)
    DENTRO_MASSA_DAGUA_VALUE = @Value(dentro_massa_dagua_value)
    DEPRESSAO_CODE = @Value(depressao_code)
    DEPRESSAO_VALUE = @Value(depressao_value)
    DESCRICAO = @Value(descricao)
    DESLOC = @Value(desloc)
    DIRECAO = @Value(direcao)
    DIRECAO_FIXADA_CODE = @Value(direcao_fixada_code)
    DIRECAO_FIXADA_VALUE = @Value(direcao_fixada_value)
    ELETRIFICADA_CODE = @Value(eletrificada_code)
    ELETRIFICADA_VALUE = @Value(eletrificada_value)
    EM_ARRUAMENTO_CODE = @Value(em_arruamento_code)
    EM_ARRUAMENTO_VALUE = @Value(em_arruamento_value)
    EM_GALERIA_BUEIRO_CODE = @Value(em_galeria_bueiro_code)
    EM_GALERIA_BUEIRO_VALUE = @Value(em_galeria_bueiro_value)
    ESCALA = @Value(escala)
    ESPACAMENTO = @Value(espacamento)
    ESTILO_FONTE = @Value(estilo_fonte)
    EXIBIR_LADO_SIMBOLOGIA_CODE = @Value(exibir_lado_simbologia_code)
    EXIBIR_LADO_SIMBOLOGIA_VALUE = @Value(exibir_lado_simbologia_value)
    EXIBIR_LINHA_ROTULO_CODE = @Value(exibir_linha_rotulo_code)
    EXIBIR_LINHA_ROTULO_VALUE = @Value(exibir_linha_rotulo_value)
    EXIBIR_PONTA_SIMBOLOGIA_CODE = @Value(exibir_ponta_simbologia_code)
    EXIBIR_PONTA_SIMBOLOGIA_VALUE = @Value(exibir_ponta_simbologia_value)
    EXIBIR_ROTULO_APROXIMADO_CODE = @Value(exibir_rotulo_aproximado_code)
    EXIBIR_ROTULO_APROXIMADO_VALUE = @Value(exibir_rotulo_aproximado_value)
    FINALIDADE_CODE = @Value(finalidade_code)
    FINALIDADE_VALUE = @Value(finalidade_value)
    FME_FEATURE_TYPE = @Value(fme_feature_type)
    FME_FEATURE_TYPE_ORIGEM = @Value(fme_feature_type_origem)
    FORMA_EXTRACAO_CODE = @Value(forma_extracao_code)
    FORMA_EXTRACAO_VALUE = @Value(forma_extracao_value)
    GEOMETRIA_APROXIMADA_CODE = @Value(geometria_aproximada_code)
    GEOMETRIA_APROXIMADA_VALUE = @Value(geometria_aproximada_value)
    GEOM_TEXTO = @Value(geom_texto)
    ID = @Value(id)
    INDICE_CODE = @Value(indice_code)
    INDICE_VALUE = @Value(indice_value)
    INOM = @Value(inom)
    JURISDICAO_CODE = @Value(jurisdicao_code)
    JURISDICAO_VALUE = @Value(jurisdicao_value)
    JUSTIFICATIVA = @Value(justificativa)
    JUSTIFICATIVA_TXT_CODE = @Value(justificativa_txt_code)
    JUSTIFICATIVA_TXT_VALUE = @Value(justificativa_txt_value)
    LABEL_X = @Value(label_x)
    LABEL_Y = @Value(label_y)
    LARGURA_SIMBOLOGIA = @Value(largura_simbologia)
    LATITUDE = @Value(latitude)
    LONGITUDE = @Value(longitude)
    MATERIAL_CONSTRUCAO_CODE = @Value(material_construcao_code)
    MATERIAL_CONSTRUCAO_ELEMENTO_VIARIO_CODE = @Value(material_construcao_elemento_viario_code)
    MATERIAL_CONSTRUCAO_ELEMENTO_VIARIO_VALUE = @Value(material_construcao_elemento_viario_value)
    MATERIAL_CONSTRUCAO_VALUE = @Value(material_construcao_value)
    MI = @Value(mi)
    MODAL_USO_CODE = @Value(modal_uso_code)
    MODAL_USO_VALUE = @Value(modal_uso_value)
    NOME = @Value(nome)
    NOME_ELEMENTO_VIARIO = @Value(nome_elemento_viario)
    NR_FAIXAS = @Value(nr_faixas)
    NR_LINHAS_CODE = @Value(nr_linhas_code)
    NR_LINHAS_VALUE = @Value(nr_linhas_value)
    NR_PISTAS = @Value(nr_pistas)
    NUMERO = @Value(numero)
    OBSERVACAO = @Value(observacao)
    ORDEM_SIMBOLOGIA = @Value(ordem_simbologia)
    ORGAO_RESPONSAVEL = @Value(orgao_responsavel)
    POPULACAO = @Value(populacao)
    POSICAO_PISTA_CODE = @Value(posicao_pista_code)
    POSICAO_PISTA_ELEMENTO_VIARIO_CODE = @Value(posicao_pista_elemento_viario_code)
    POSICAO_PISTA_ELEMENTO_VIARIO_VALUE = @Value(posicao_pista_elemento_viario_value)
    POSICAO_PISTA_VALUE = @Value(posicao_pista_value)
    POSICAO_RELATIVA_CODE = @Value(posicao_relativa_code)
    POSICAO_RELATIVA_VALUE = @Value(posicao_relativa_value)
    POSICAO_ROTULO_CODE = @Value(posicao_rotulo_code)
    POSICAO_ROTULO_VALUE = @Value(posicao_rotulo_value)
    REFERENCIAL_ALTIM_CODE = @Value(referencial_altim_code)
    REFERENCIAL_ALTIM_VALUE = @Value(referencial_altim_value)
    REFERENCIAL_GRAV_CODE = @Value(referencial_grav_code)
    REFERENCIAL_GRAV_VALUE = @Value(referencial_grav_value)
    REGIME_CODE = @Value(regime_code)
    REGIME_VALUE = @Value(regime_value)
    REVESTIMENTO_CODE = @Value(revestimento_code)
    REVESTIMENTO_VALUE = @Value(revestimento_value)
    SIGLA = @Value(sigla)
    SIGLA_CODE = @Value(sigla_code)
    SIGLA_VALUE = @Value(sigla_value)
    SIMB_ROT = @Value(simb_rot)
    SISTEMA_GEODESICO_CODE = @Value(sistema_geodesico_code)
    SISTEMA_GEODESICO_VALUE = @Value(sistema_geodesico_value)
    SITUACAO_EM_POLIGONO_CODE = @Value(situacao_em_poligono_code)
    SITUACAO_EM_POLIGONO_VALUE = @Value(situacao_em_poligono_value)
    SITUACAO_FISICA_CODE = @Value(situacao_fisica_code)
    SITUACAO_FISICA_VALUE = @Value(situacao_fisica_value)
    SITUACAO_MARCO_CODE = @Value(situacao_marco_code)
    SITUACAO_MARCO_VALUE = @Value(situacao_marco_value)
    SOBREPOSTO_CODE = @Value(sobreposto_code)
    SOBREPOSTO_TRANSPORTES_CODE = @Value(sobreposto_transportes_code)
    SOBREPOSTO_TRANSPORTES_VALUE = @Value(sobreposto_transportes_value)
    SOBREPOSTO_VALUE = @Value(sobreposto_value)
    SUBFASE_ID = @Value(subfase_id)
    SUJEITO_INUNDACAO_CODE = @Value(sujeito_inundacao_code)
    SUJEITO_INUNDACAO_VALUE = @Value(sujeito_inundacao_value)
    SUPRIMIR_BANDEIRA_CODE = @Value(suprimir_bandeira_code)
    SUPRIMIR_BANDEIRA_VALUE = @Value(suprimir_bandeira_value)
    SUPRIMIR_SIMBOLOGIA_CODE = @Value(suprimir_simbologia_code)
    SUPRIMIR_SIMBOLOGIA_VALUE = @Value(suprimir_simbologia_value)
    TAMANHO_TXT = @Value(tamanho_txt)
    TEXTO_EDICAO = @Value(texto_edicao)
    TIPO_CODE = @Value(tipo_code)
    TIPO_ELEMENTO_VIARIO_CODE = @Value(tipo_elemento_viario_code)
    TIPO_ELEMENTO_VIARIO_VALUE = @Value(tipo_elemento_viario_value)
    TIPO_EXPOSICAO_CODE = @Value(tipo_exposicao_code)
    TIPO_EXPOSICAO_VALUE = @Value(tipo_exposicao_value)
    TIPO_GRID = @Value(tipo_grid)
    TIPO_PRODUTO_CODE = @Value(tipo_produto_code)
    TIPO_PRODUTO_VALUE = @Value(tipo_produto_value)
    TIPO_REF_CODE = @Value(tipo_ref_code)
    TIPO_REF_VALUE = @Value(tipo_ref_value)
    TIPO_VALUE = @Value(tipo_value)
    TRAFEGO_CODE = @Value(trafego_code)
    TRAFEGO_VALUE = @Value(trafego_value)
    USO_PISTA_CODE = @Value(uso_pista_code)
    USO_PISTA_VALUE = @Value(uso_pista_value)
    VEG_MIN_100K = 250000
    VISIVEL_CODE = @Value(visivel_code)
    VISIVEL_VALUE = @Value(visivel_value)
    FeatureMerger_Merged -> DonutHoleExtractor
DonutHoleExtractor
    DEAGGREGATE_INPUT = Yes
    OUTERSHELL -> Cobertura
    OUTERSHELL -> Tester_7
    OUTERSHELL -> Junction_5
Tester_7
    BOOL_OP = OR
    TEST_CLAUSE = TEST @Value(fme_feature_type_origem) = edgv.cobter_area_edificada_a
    TEST_MODE = TEST
    PASSED -> Generalizar_Edificacao [PointOnAreaOverlayer_Area]
Cobertura: Inspector [off]
    TACKATTRS = fme_feature_type_origem
Generalizar_area_5
    ADMINISTRACAO_CODE = @Value(administracao_code)
    ADMINISTRACAO_VALUE = @Value(administracao_value)
    ALTITUDE = @Value(altitude)
    ALTITUDE_GEOMETRICA = @Value(altitude_geometrica)
    ALTITUDE_ORTOMETRICA = @Value(altitude_ortometrica)
    ALTURA = @Value(altura)
    ANCORA_HORIZONTAL_CODE = @Value(ancora_horizontal_code)
    ANCORA_HORIZONTAL_VALUE = @Value(ancora_horizontal_value)
    ANCORA_VERTICAL_CODE = @Value(ancora_vertical_code)
    ANCORA_VERTICAL_VALUE = @Value(ancora_vertical_value)
    AREA_MINIMA_VALOR = @Value(area_minima_valor)
    ASSENTAMENTO_PRECARIO_CODE = @Value(assentamento_precario_code)
    ASSENTAMENTO_PRECARIO_VALUE = @Value(assentamento_precario_value)
    BITOLA_CODE = @Value(bitola_code)
    BITOLA_VALUE = @Value(bitola_value)
    CANTEIRO_DIVISORIO_CODE = @Value(canteiro_divisorio_code)
    CANTEIRO_DIVISORIO_VALUE = @Value(canteiro_divisorio_value)
    COD_PONTO = @Value(cod_ponto)
    CONCESSIONARIA = @Value(concessionaria)
    CONFIG_COMPRIMENTO_SIMB_CODE = @Value(config_comprimento_simb_code)
    CONFIG_COMPRIMENTO_SIMB_VALUE = @Value(config_comprimento_simb_value)
    COR = @Value(cor)
    CORRIGIDO_CODE = @Value(corrigido_code)
    CORRIGIDO_VALUE = @Value(corrigido_value)
    COTA = @Value(cota)
    COTA_COMPROVADA_CODE = @Value(cota_comprovada_code)
    COTA_COMPROVADA_VALUE = @Value(cota_comprovada_value)
    COTA_MAIS_ALTA_CODE = @Value(cota_mais_alta_code)
    COTA_MAIS_ALTA_VALUE = @Value(cota_mais_alta_value)
    DENTRO_MASSA_DAGUA_CODE = @Value(dentro_massa_dagua_code)
    DENTRO_MASSA_DAGUA_VALUE = @Value(dentro_massa_dagua_value)
    DEPRESSAO_CODE = @Value(depressao_code)
    DEPRESSAO_VALUE = @Value(depressao_value)
    DESCRICAO = @Value(descricao)
    DESLOC = @Value(desloc)
    DIRECAO = @Value(direcao)
    DIRECAO_FIXADA_CODE = @Value(direcao_fixada_code)
    DIRECAO_FIXADA_VALUE = @Value(direcao_fixada_value)
    ELETRIFICADA_CODE = @Value(eletrificada_code)
    ELETRIFICADA_VALUE = @Value(eletrificada_value)
    EM_ARRUAMENTO_CODE = @Value(em_arruamento_code)
    EM_ARRUAMENTO_VALUE = @Value(em_arruamento_value)
    EM_GALERIA_BUEIRO_CODE = @Value(em_galeria_bueiro_code)
    EM_GALERIA_BUEIRO_VALUE = @Value(em_galeria_bueiro_value)
    ESCALA = @Value(escala)
    ESPACAMENTO = @Value(espacamento)
    ESTILO_FONTE = @Value(estilo_fonte)
    EXIBIR_LADO_SIMBOLOGIA_CODE = @Value(exibir_lado_simbologia_code)
    EXIBIR_LADO_SIMBOLOGIA_VALUE = @Value(exibir_lado_simbologia_value)
    EXIBIR_LINHA_ROTULO_CODE = @Value(exibir_linha_rotulo_code)
    EXIBIR_LINHA_ROTULO_VALUE = @Value(exibir_linha_rotulo_value)
    EXIBIR_PONTA_SIMBOLOGIA_CODE = @Value(exibir_ponta_simbologia_code)
    EXIBIR_PONTA_SIMBOLOGIA_VALUE = @Value(exibir_ponta_simbologia_value)
    EXIBIR_ROTULO_APROXIMADO_CODE = @Value(exibir_rotulo_aproximado_code)
    EXIBIR_ROTULO_APROXIMADO_VALUE = @Value(exibir_rotulo_aproximado_value)
    FINALIDADE_CODE = @Value(finalidade_code)
    FINALIDADE_VALUE = @Value(finalidade_value)
    FME_FEATURE_TYPE = @Value(fme_feature_type)
    FME_FEATURE_TYPE_ORIGEM = @Value(fme_feature_type_origem)
    FORMA_EXTRACAO_CODE = @Value(forma_extracao_code)
    FORMA_EXTRACAO_VALUE = @Value(forma_extracao_value)
    GEOMETRIA_APROXIMADA_CODE = @Value(geometria_aproximada_code)
    GEOMETRIA_APROXIMADA_VALUE = @Value(geometria_aproximada_value)
    GEOM_TEXTO = @Value(geom_texto)
    ID = @Value(id)
    INDICE_CODE = @Value(indice_code)
    INDICE_VALUE = @Value(indice_value)
    INOM = @Value(inom)
    JURISDICAO_CODE = @Value(jurisdicao_code)
    JURISDICAO_VALUE = @Value(jurisdicao_value)
    JUSTIFICATIVA = @Value(justificativa)
    JUSTIFICATIVA_TXT_CODE = @Value(justificativa_txt_code)
    JUSTIFICATIVA_TXT_VALUE = @Value(justificativa_txt_value)
    LABEL_X = @Value(label_x)
    LABEL_Y = @Value(label_y)
    LARGURA_SIMBOLOGIA = @Value(largura_simbologia)
    LATITUDE = @Value(latitude)
    LONGITUDE = @Value(longitude)
    MATERIAL_CONSTRUCAO_CODE = @Value(material_construcao_code)
    MATERIAL_CONSTRUCAO_ELEMENTO_VIARIO_CODE = @Value(material_construcao_elemento_viario_code)
    MATERIAL_CONSTRUCAO_ELEMENTO_VIARIO_VALUE = @Value(material_construcao_elemento_viario_value)
    MATERIAL_CONSTRUCAO_VALUE = @Value(material_construcao_value)
    MI = @Value(mi)
    MODAL_USO_CODE = @Value(modal_uso_code)
    MODAL_USO_VALUE = @Value(modal_uso_value)
    NOME = @Value(nome)
    NOME_ELEMENTO_VIARIO = @Value(nome_elemento_viario)
    NR_FAIXAS = @Value(nr_faixas)
    NR_LINHAS_CODE = @Value(nr_linhas_code)
    NR_LINHAS_VALUE = @Value(nr_linhas_value)
    NR_PISTAS = @Value(nr_pistas)
    NUMERO = @Value(numero)
    OBSERVACAO = @Value(observacao)
    ORDEM_SIMBOLOGIA = @Value(ordem_simbologia)
    ORGAO_RESPONSAVEL = @Value(orgao_responsavel)
    POPULACAO = @Value(populacao)
    POSICAO_PISTA_CODE = @Value(posicao_pista_code)
    POSICAO_PISTA_ELEMENTO_VIARIO_CODE = @Value(posicao_pista_elemento_viario_code)
    POSICAO_PISTA_ELEMENTO_VIARIO_VALUE = @Value(posicao_pista_elemento_viario_value)
    POSICAO_PISTA_VALUE = @Value(posicao_pista_value)
    POSICAO_RELATIVA_CODE = @Value(posicao_relativa_code)
    POSICAO_RELATIVA_VALUE = @Value(posicao_relativa_value)
    POSICAO_ROTULO_CODE = @Value(posicao_rotulo_code)
    POSICAO_ROTULO_VALUE = @Value(posicao_rotulo_value)
    REFERENCIAL_ALTIM_CODE = @Value(referencial_altim_code)
    REFERENCIAL_ALTIM_VALUE = @Value(referencial_altim_value)
    REFERENCIAL_GRAV_CODE = @Value(referencial_grav_code)
    REFERENCIAL_GRAV_VALUE = @Value(referencial_grav_value)
    REGIME_CODE = @Value(regime_code)
    REGIME_VALUE = @Value(regime_value)
    REVESTIMENTO_CODE = @Value(revestimento_code)
    REVESTIMENTO_VALUE = @Value(revestimento_value)
    SIGLA = @Value(sigla)
    SIGLA_CODE = @Value(sigla_code)
    SIGLA_VALUE = @Value(sigla_value)
    SIMB_ROT = @Value(simb_rot)
    SISTEMA_GEODESICO_CODE = @Value(sistema_geodesico_code)
    SISTEMA_GEODESICO_VALUE = @Value(sistema_geodesico_value)
    SITUACAO_EM_POLIGONO_CODE = @Value(situacao_em_poligono_code)
    SITUACAO_EM_POLIGONO_VALUE = @Value(situacao_em_poligono_value)
    SITUACAO_FISICA_CODE = @Value(situacao_fisica_code)
    SITUACAO_FISICA_VALUE = @Value(situacao_fisica_value)
    SITUACAO_MARCO_CODE = @Value(situacao_marco_code)
    SITUACAO_MARCO_VALUE = @Value(situacao_marco_value)
    SOBREPOSTO_CODE = @Value(sobreposto_code)
    SOBREPOSTO_TRANSPORTES_CODE = @Value(sobreposto_transportes_code)
    SOBREPOSTO_TRANSPORTES_VALUE = @Value(sobreposto_transportes_value)
    SOBREPOSTO_VALUE = @Value(sobreposto_value)
    SUBFASE_ID = @Value(subfase_id)
    SUJEITO_INUNDACAO_CODE = @Value(sujeito_inundacao_code)
    SUJEITO_INUNDACAO_VALUE = @Value(sujeito_inundacao_value)
    SUPRIMIR_BANDEIRA_CODE = @Value(suprimir_bandeira_code)
    SUPRIMIR_BANDEIRA_VALUE = @Value(suprimir_bandeira_value)
    SUPRIMIR_SIMBOLOGIA_CODE = @Value(suprimir_simbologia_code)
    SUPRIMIR_SIMBOLOGIA_VALUE = @Value(suprimir_simbologia_value)
    TAMANHO_TXT = @Value(tamanho_txt)
    TEXTO_EDICAO = @Value(texto_edicao)
    TIPO_CODE = @Value(tipo_code)
    TIPO_ELEMENTO_VIARIO_CODE = @Value(tipo_elemento_viario_code)
    TIPO_ELEMENTO_VIARIO_VALUE = @Value(tipo_elemento_viario_value)
    TIPO_EXPOSICAO_CODE = @Value(tipo_exposicao_code)
    TIPO_EXPOSICAO_VALUE = @Value(tipo_exposicao_value)
    TIPO_GRID = @Value(tipo_grid)
    TIPO_PRODUTO_CODE = @Value(tipo_produto_code)
    TIPO_PRODUTO_VALUE = @Value(tipo_produto_value)
    TIPO_REF_CODE = @Value(tipo_ref_code)
    TIPO_REF_VALUE = @Value(tipo_ref_value)
    TIPO_VALUE = @Value(tipo_value)
    TRAFEGO_CODE = @Value(trafego_code)
    TRAFEGO_VALUE = @Value(trafego_value)
    USO_PISTA_CODE = @Value(uso_pista_code)
    USO_PISTA_VALUE = @Value(uso_pista_value)
    VEG_MIN_100K = 250000
    VISIVEL_CODE = @Value(visivel_code)
    VISIVEL_VALUE = @Value(visivel_value)
    FeatureMerger_Merged -> TSI_100k
    FeatureMerger_Merged -> Junction_5
    NeighborFinder_UnmatchedBase -> TSI_Não_toca_em_outra_Veg_2
    NeighborFinder_UnmatchedBase -> Junction_5
TSI_100k: Inspector [off]
Junction_5
    -> AttributeCreator_3
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(fme_feature_type_origem) = edgv.cobter_massa_dagua_a",massa_dagua,"BOOL_OP,OR,COMPOSITE_TEST,""""""1"""""",TEST_CLAUSE,TEST @Value(fme_feature_type_origem) = edgv.cobter_area_edificada_a",area_edificada
    area_edificada -> AttributeCreator_7
    massa_dagua -> Junction_8
Junction_8
    -> Generalizar_curvas_nivel [LineOnAreaOverlayer_Area]
    -> PointOnAreaOverlayer [AREA]
AttributeCreator_7
    ATTR_TABLE = SET_TO _escala_parea_generalizar (varchar(200)) = $(generelizar_para_ESCALA)
    -> Generalizar_localidade [Tester_9_Input]
TSI_Não_toca_em_outra_Veg_2: Inspector [off]
Reprojector_2
    DEST = $(EPSG)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Snapper
Snapper
    EXTEND_LINES = NEVER
    GROUP_BY = fme_feature_type tipo_code
    SAVE_SHORT_LINES = No
    SNAPTYPE = END_NODE
    TOLERANCE = 5
    SNAPPED -> LineCombiner
    UNTOUCHED -> LineCombiner
LineCombiner
    ACCUM_ATTRS_NAME = Use Attributes From One Feature
    BREAK_CONNECTION_ATTRIBUTES = fme_feature_type tipo_code
    CLOSE = yes
    CONNECT_Z_MODE_LOOKUP = FIRST_WINS
    CONSIDER_NODE_ELEVATION_LOOKUP = NO
    DEAGGREGATE_GEOMETRY = Deaggregate
    JUNCTIONS_IGNORE_ATTRIBUTES = Yes
    LINES_AS_SEGMENTS = No
    NODED = END_NODED
    PRESERVE = no
    BREAK = no
    CONNECT_Z_MODE = First Wins
    CONSIDER_NODE_ELEVATION = no
    TOPOLOGY = End Noded
    LINE -> TestFilter_2
TestFilter_2
    DEFAULT_VALUE = <UNFILTERED>
    PASSED_TEST_GROUP_OUTPUT = FIRST
    TEST_LIST = "BOOL_OP,OR,COMPOSITE_TEST,""""""1"""""",TEST_CLAUSE,TEST $(generelizar_para_ESCALA) = 50",50.000,"BOOL_OP,OR,COMPOSITE_TEST,""""""1"""""",TEST_CLAUSE,TEST $(generelizar_para_ESCALA) = 100",100.000,"BOOL_OP,OR,COMPOSITE_TEST,""""""1"""""",TEST_CLAUSE,TEST $(generelizar_para_ESCALA) = 250",250.000
    100.000 -> comprimento_minimo_valor_100K
    250.000 -> comprimento_minimo_valor_250K
comprimento_minimo_valor_100K: AttributeCreator
    ATTR_TABLE:
      SET_TO comprimento_minimo_valor (varchar(200)) = FME_CONDITIONAL:DEFAULT_VALUE'_FME_NO_OP_'BOOL_OP;OR;COMPOSITE_TEST;1;TEST @Value(fme_feature_type_origem) = edgv.infra_via_deslocamento_l'1000'BOOL_OP;OR;COMPOSITE_TEST;1;TEST @Value(fme_feature_type_origem) = edgv.infra_vala_l'1000'BOOL_OP;AND;COMPOSITE_TEST;1 AND 2 AND 3;TEST @Value(fme_feature_type_origem) = edgv.infra_trecho_duto_l;TEST @Value(tipo_code) > 301;TEST @Value(tipo_code) < 309'1'BOOL_OP;AND;COMPOSITE_TEST;1 AND 2 AND 3;TEST @Value(fme_feature_type_origem) = edgv.infra_trecho_duto_l;TEST @Value(tipo_code) <= 301;TEST @Value(tipo_code) >= 309'0'BOOL_OP;OR;COMPOSITE_TEST;1;TEST @Value(fme_feature_type_origem) = edgv.infra_travessia_hidroviaria_l'1000'BOOL_OP;OR;COMPOSITE_TEST;1;TEST @Value(fme_feature_type_origem) = edgv.infra_pista_pouso_l'800'BOOL_OP;OR;COMPOSITE_TEST;1;TEST @Value(fme_feature_type_origem) = edgv.infra_ferrovia_l'0'BOOL_OP;OR;COMPOSITE_TEST;1;TEST @Value(fme_feature_type_origem) = edgv.infra_elemento_viario_l'0'BOOL_OP;AND;COMPOSITE_TEST;1;TEST @Value(fme_feature_type_origem) = edgv.infra_elemento_infraestrutura_l'0'BOOL_OP;AND;COMPOSITE_TEST;1;TEST @Value(fme_feature_type_origem) = edgv.infra_barragem_l'100'BOOL_OP;OR;COMPOSITE_TEST;1;TEST @Value(fme_feature_type_origem) = edgv.infra_alteracao_fisiografica_antropica_l'200'BOOL_OP;OR;COMPOSITE_TEST;1;TEST @Value(fme_feature_type_origem) = edgv.elemnat_trecho_drenagem_l'1000'BOOL_OP;OR;COMPOSITE_TEST;1;TEST @Value(fme_feature_type_origem) = edgv.elemnat_toponimo_fisiografico_natural_l'0'BOOL_OP;OR;COMPOSITE_TEST;1;TEST @Value(fme_feature_type_origem) = edgv.elemnat_curva_nivel_l'40'BOOL_OP;OR;COMPOSITE_TEST;1;TEST @Value(fme_feature_type_origem) = edgv.constr_ocupacao_solo_l'0'FME_NUM_CONDITIONS16___
      SET_TO comprimento (varchar(200)) = @Length()
    -> AttributeFilter_3
comprimento_minimo_valor_250K: AttributeCreator
    ATTR_TABLE:
      SET_TO comprimento_minimo_valor (varchar(200)) = FME_CONDITIONAL:DEFAULT_VALUE'_FME_NO_OP_'BOOL_OP;OR;COMPOSITE_TEST;1;TEST @Value(fme_feature_type_origem) = edgv.infra_via_deslocamento_l'2500'BOOL_OP;OR;COMPOSITE_TEST;1;TEST @Value(fme_feature_type_origem) = edgv.infra_vala_l'2500'BOOL_OP;AND;COMPOSITE_TEST;1 AND 2 AND 3;TEST @Value(fme_feature_type_origem) = edgv.infra_trecho_duto_l;TEST @Value(tipo_code) > 301;TEST @Value(tipo_code) < 309'1'BOOL_OP;AND;COMPOSITE_TEST;1 AND 2 AND 3;TEST @Value(fme_feature_type_origem) = edgv.infra_trecho_duto_l;TEST @Value(tipo_code) <= 301;TEST @Value(tipo_code) >= 309'0'BOOL_OP;OR;COMPOSITE_TEST;1;TEST @Value(fme_feature_type_origem) = edgv.infra_travessia_hidroviaria_l'2500'BOOL_OP;OR;COMPOSITE_TEST;1;TEST @Value(fme_feature_type_origem) = edgv.infra_pista_pouso_l'2000'BOOL_OP;OR;COMPOSITE_TEST;1;TEST @Value(fme_feature_type_origem) = edgv.infra_ferrovia_l'0'BOOL_OP;OR;COMPOSITE_TEST;1;TEST @Value(fme_feature_type_origem) = edgv.infra_elemento_viario_l'0'BOOL_OP;AND;COMPOSITE_TEST;1;TEST @Value(fme_feature_type_origem) = edgv.infra_elemento_infraestrutura_l'0'BOOL_OP;AND;COMPOSITE_TEST;1;TEST @Value(fme_feature_type_origem) = edgv.infra_barragem_l'250'BOOL_OP;OR;COMPOSITE_TEST;1;TEST @Value(fme_feature_type_origem) = edgv.infra_alteracao_fisiografica_antropica_l'500'BOOL_OP;OR;COMPOSITE_TEST;1;TEST @Value(fme_feature_type_origem) = edgv.elemnat_trecho_drenagem_l'2500'BOOL_OP;OR;COMPOSITE_TEST;1;TEST @Value(fme_feature_type_origem) = edgv.elemnat_toponimo_fisiografico_natural_l'0'BOOL_OP;OR;COMPOSITE_TEST;1;TEST @Value(fme_feature_type_origem) = edgv.elemnat_curva_nivel_l'100'BOOL_OP;OR;COMPOSITE_TEST;1;TEST @Value(fme_feature_type_origem) = edgv.constr_ocupacao_solo_l'0'FME_NUM_CONDITIONS16___
      SET_TO comprimento (varchar(200)) = @Length()
    -> AttributeFilter_3
AttributeFilter_3
    ATTR_NAME = fme_feature_type_origem
    ATTR_VALUES = <Empty>,<Missing>,<Null>,<Unfiltered>,edgv.infra_via_deslocamento_l,edgv.elemnat_trecho_drenagem_l,edgv.infra_vala_l,edgv.infra_trecho_duto_l,edgv.infra_travessia_hidroviaria_l,edgv.infra_pista_pouso_l,edgv.infra_ferrovia_l,edgv.infra_elemento_energia_l,edgv.infra_barragem_l,edgv.infra_alteracao_fisiografica_antropica_l,edgv.elemnat_toponimo_fisiografico_natural_l,edgv.elemnat_curva_nivel_l,edgv.constr_ocupacao_solo_l,edgv.infra_elemento_infraestrutura_l,edgv.infra_elemento_viario_l
    edgv.infra_via_deslocamento_l -> Remover_linhas_soltas [Intersector_Input]
    edgv.elemnat_trecho_drenagem_l -> Remover_linhas_soltas_2 [Intersector_Input]
    edgv.infra_vala_l -> Tester_3
    edgv.infra_trecho_duto_l -> Tester_3
    edgv.infra_travessia_hidroviaria_l -> Tester_3
    edgv.infra_pista_pouso_l -> Tester_3
    edgv.infra_ferrovia_l -> Tester_3
    edgv.infra_elemento_energia_l -> Tester_3
    edgv.infra_barragem_l -> Tester_3
    edgv.infra_alteracao_fisiografica_antropica_l -> Tester_3
    edgv.elemnat_toponimo_fisiografico_natural_l -> Tester_3
    edgv.elemnat_curva_nivel_l -> Generalizar_curvas_nivel [Tester_Input]
Remover_linhas_soltas
    Tester_Passed -> Tester_5
Tester_5
    BOOL_OP = COMPOSITE
    COMPOSITE_TEST = 1 AND (( 2 AND 3 ) OR ( 4 AND 5 AND 6 ))
    TEST_CLAUSE:
      TEST @Value(fme_feature_type_origem) = edgv.infra_via_deslocamento_l
      TEST @Value(tipo_code) = 3
      TEST @Value(comprimento) > @Value(comprimento_minimo_valor)
      TEST @Value(tipo_code) != 3
      TEST @Value(tipo_code) != 5
      TEST @Value(tipo_code) != 9999
    TEST_MODE = TEST
    PASSED -> Junction_4
Remover_linhas_soltas_2
    Tester_Passed -> Junction_4
Tester_3
    BOOL_OP = AND
    TEST_CLAUSE = TEST @Value(comprimento) >= @Value(comprimento_minimo_valor)
    TEST_MODE = TEST
    PASSED -> Junction_4
Generalizar_curvas_nivel
    COMPRIMENTO_MINIMO_VALOR = @Value(comprimento_minimo_valor)
    COTA = @Value(cota)
    Tester_8_Passed -> Junction_4
Junction_4
    -> Linhas
    -> AttributeCreator_3
Linhas: Inspector [off]
    TACKATTRS = fme_feature_type_origem
Reprojector_3
    DEST = $(EPSG)
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> AttributeFilter_4
AttributeFilter_4
    ATTR_NAME = fme_feature_type_origem
    ATTR_VALUES = <Empty>,<Missing>,<Null>,<Unfiltered>,edgv.constr_edificacao_p,edgv.elemnat_ponto_cotado_p,edgv.constr_ocupacao_solo_p,edgv.constr_extracao_mineral_p,edgv.elemnat_elemento_hidrografico_p,edgv.elemnat_sumidouro_vertedouro_p,edgv.elemnat_toponimo_fisiografico_natural_p,edgv.infra_elemento_energia_p,edgv.infra_pista_pouso_p,edgv.llp_ponto_controle_p,edgv.llp_localidade_p
    edgv.constr_edificacao_p -> AttributeCreator_2
    edgv.elemnat_ponto_cotado_p -> Filtrar_cotas [PointOnAreaOverlayer_2_Point]
    edgv.constr_ocupacao_solo_p -> Tester_4
    edgv.constr_extracao_mineral_p -> Junction
    edgv.elemnat_elemento_hidrografico_p -> Junction
    edgv.elemnat_sumidouro_vertedouro_p -> Junction
    edgv.elemnat_toponimo_fisiografico_natural_p -> Junction
    edgv.infra_elemento_energia_p -> Junction
    edgv.infra_pista_pouso_p -> Junction
    edgv.llp_localidade_p -> AttributeCreator_6
    edgv.llp_ponto_controle_p -> Junction
AttributeCreator_2
    ATTR_TABLE = SET_TO _escala_parea_generalizar (varchar(200)) = $(generelizar_para_ESCALA)
    -> Generalizar_Edificacao [PointOnAreaOverlayer_Point]
Generalizar_Edificacao
    FME_FEATURE_TYPE_ORIGEM = @Value(fme_feature_type_origem)
    TIPO_CODE = @Value(tipo_code)
    _ESCALA_PAREA_GENERALIZAR = @Value(_escala_parea_generalizar)
    Eif_Genereicas_Filtradas -> Junction_3
    Edif_outras -> Junction_3
Filtrar_cotas
    COTA = @Value(cota)
    ID = @Value(id)
    ID_CELULAR_GRID = @Value(id_celular_grid)
    Tester_6_Passed -> Junction_3
Tester_4
    BOOL_OP = COMPOSITE
    COMPOSITE_TEST = 1 AND ( 2 OR 3 OR 4 )
    TEST_CLAUSE:
      TEST @Value(fme_feature_type_origem) = edgv.constr_ocupacao_solo_p
      TEST @Value(tipo_code) = 1101
      TEST @Value(tipo_code) = 1201
      TEST @Value(tipo_code) = 1202
    TEST_MODE = TEST
    PASSED -> Junction_3
Junction
    -> Junction_3
AttributeCreator_6
    ATTR_TABLE = SET_TO _escala_parea_generalizar (varchar(200)) = $(generelizar_para_ESCALA)
    -> Generalizar_localidade [TestFilter_4_Input]
Generalizar_localidade
    NOME = @Value(nome)
    TIPO_CODE = @Value(tipo_code)
    generelizar_para_ESCALA = 100
    Junction_9_Output -> Junction_3
    Junction_9_Output -> Generalizar_localidade_Junction_9_Output
Junction_3
    -> PointOnAreaOverlayer [POINT]
PointOnAreaOverlayer
    DEAGGREGATE_INPUT = Yes
    OV_ATTR = _overlaps_pt_massa_dagua
    POLYS_FIRST = NO
    POINT -> Tester_6
Tester_6
    BOOL_OP = OR
    TEST_CLAUSE = TEST @Value(_overlaps_pt_massa_dagua) = 0
    TEST_MODE = TEST
    PASSED -> Pontos
    PASSED -> AttributeCreator_3
AttributeCreator_3
    ATTR_TABLE = SET_TO fme_feature_type_destino (varchar(200)) = @Substring(@Value(fme_feature_type_origem), 5, @StringLength(@Value(fme_feature_type_origem)) - 7)_$(generelizar_para_ESCALA)k_@Value(geom_texto)
    -> Conversao
    -> UniqueIdentifierGenerator
Conversao: Inspector
    TACKATTRS = fme_feature_type_destino
UniqueIdentifierGenerator
    UUID_ATTR = id
    UUID_FORMAT = UUID_ONLY
    -> Reprojector
Reprojector
    DEST = EPSG:4674
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> CollectionToMulti
CollectionToMulti
    -> Table1 (writer POSTGIS_2)
Table1 (writer POSTGIS_2)
Pontos: Inspector [off]
    TACKATTRS = fme_feature_type
Generalizar_localidade_Junction_9_Output: Inspector

Bookmark: Grid
Junction_7
    -> BoundsExtractor
BoundsExtractor
    XMAX = _xmax
    XMIN = _xmin
    YMAX = _ymax
    YMIN = _ymin
    ZMAX = _zmax
    ZMIN = _zmin
    -> AttributeCreator_4
AttributeCreator_4
    ATTR_TABLE:
      SET_TO _x_min_grid (real64) = @Evaluate(@mult(@floor(@div(@Value(_xmin),1000.0),0),1000))
      SET_TO _y_max_grid (real64) = @Evaluate(@mult(@ceil(@div(@Value(_ymax),1000.0),0),1000))
    -> 2DGridAccumulator_2
2DGridAccumulator_2
    BBOX_TYPE = GRID_POLYGONS
    COL_ATTR = _column
    GRID_ORIGIN = TOP_LEFT
    ROW_ATTR = _row
    SIZE_TYPE = Cell Size
    XINC = $(generelizar_para_ESCALA) * 10 * 4
    XSEED = @Value(_x_min_grid)
    YINC = $(generelizar_para_ESCALA) * 10 * 4
    YSEED = @Value(_y_max_grid)
    GRID_TYPE = Polygons
    STARTINGCORNER = Upper Left
    GRID -> AttributeCreator_5
AttributeCreator_5
    ATTR_TABLE:
      SET_TO fme_feature_type (varchar(12)) = linhas_gride
      SET_TO id_celular_grid (varchar(200)) = @Value(_row)_@Value(_column)
    -> Grid
    -> Filtrar_cotas [AttributeKeeper_19_Input]
Grid: Inspector

FME custom transformer Generalizar_curvas_nivel

Parameters:
- COMPRIMENTO_MINIMO_VALOR = @Value(comprimento_minimo_valor)   # Comprimento Minimo Valor
- COTA = @Value(cota)   # cota

Tester_Input (input)
    -> Tester
Tester
    BOOL_OP = OR
    TEST_CLAUSE = TEST @Evaluate(@Value(cota) % @Value(comprimento_minimo_valor)) = 0
    TEST_MODE = TEST
    PASSED -> AttributeCreator
AttributeCreator
    ATTR_TABLE = SET_TO indice_code (int16) = FME_CONDITIONAL:DEFAULT_VALUE'2'BOOL_OP;OR;COMPOSITE_TEST;1;TEST @Evaluate(@Value(cota) % (@Value(comprimento_minimo_valor) * 5)) = 0'1'FME_NUM_CONDITIONS2___
    -> LineOnAreaOverlayer [LINE]
LineOnAreaOverlayer_Area (input)
    -> LineOnAreaOverlayer [AREA]
LineOnAreaOverlayer
    CLEANING_TOLERANCE_LOOKUP = AUTO
    DEAGGREGATE_INPUT = Yes
    OVERLAY_TYPE = LINE_ON_AREA
    OV_ATTR = _overlaps_curva_massa_dagua
    CLEANING_TOLERANCE = Automatic
    LINE -> Tester_8
Tester_8
    BOOL_OP = OR
    TEST_CLAUSE = TEST @Value(_overlaps_curva_massa_dagua) = 0
    TEST_MODE = TEST
    PASSED -> Tester_8_Passed (output)
Tester_8_Passed (output)

FME custom transformer Generalizar_localidade

Parameters:
- generelizar_para_ESCALA = 100
- TIPO_CODE = @Value(tipo_code)   # Tipo Code
- NOME = @Value(nome)   # nome

TestFilter_4_Input (input)
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST $(generelizar_para_ESCALA) = 50",50.000,"BOOL_OP,OR,COMPOSITE_TEST,""""""1"""""",TEST_CLAUSE,TEST $(generelizar_para_ESCALA) = 100",100.000,"BOOL_OP,OR,COMPOSITE_TEST,""""""1"""""",TEST_CLAUSE,TEST $(generelizar_para_ESCALA) = 250",250.000
    50.000 -> Junction_9
    100.000 -> Tester_11
    250.000 -> Tester
Tester_11
    BOOL_OP = OR
    TEST_CLAUSE = TEST @Value(tipo_code) = 1
    TEST_MODE = TEST
    PASSED -> Junction_9
    FAILED -> FeatureMerger [SUPPLIER]
Tester
    BOOL_OP = OR
    TEST_CLAUSE = TEST @Value(tipo_code) = 1
    TEST_MODE = TEST
    PASSED -> Junction_9
Tester_9_Input (input)
    -> Tester_9
Tester_9
    BOOL_OP = AND
    TEST_CLAUSE:
      TEST $(generelizar_para_ESCALA) = 100
      TEST nome ATTRIBUTE_HAS_A_VALUE ""
    TEST_MODE = TEST
    PASSED -> CenterPointReplacer
CenterPointReplacer
    POINTTYPE = CENTER
    POINT -> AttributeKeeper
AttributeKeeper
    CREATE_BULK_MODE_FEATURES = NO
    KEEP_ATTRS = nome
    -> FeatureMerger [REQUESTOR]
FeatureMerger
    ATTR_ACCUM_MODE = Merge Supplier
    ATTR_CONFLICT_RES_LOOKUP = REQUESTOR_IF_CONFLICT
    IGNORE_NULLS = No
    JOIN_KEYS = @Value(nome) @Value(nome) AUTO
    MERGE_TYPE = Attributes Only
    PROCESS_DUPS = NO
    REJECT_NULL_MISSING_KEYS = No
    SUPPLIERS_FIRST = No
    ATTR_CONFLICT_RES = Use Requestor
    MERGED -> Junction_9
    UNMERGED_REQUESTOR -> AttributeCreator_7
AttributeCreator_7
    ATTR_TABLE:
      SET_TO observacao (varchar(25)) = gerado por area edificada
      SET_TO tipo_code (uint8) = 8
      SET_TO tipo_value (varchar(10)) = Nome Local
      SET_TO fme_feature_type_origem (varchar(21)) = edgv.llp_localidade_p
      SET_TO geom_texto (varchar(1)) = p
      SET_TO id (char(36))
    -> Junction_9
Junction_9
    -> Junction_9_Output (output)
Junction_9_Output (output)

FME custom transformer Generalizar_Edificacao

Parameters:
- TIPO_CODE = @Value(tipo_code)   # Tipo Code
- FME_FEATURE_TYPE_ORIGEM = @Value(fme_feature_type_origem)   # Fme Feature Type Origem
- _ESCALA_PAREA_GENERALIZAR = @Value(_escala_parea_generalizar)   # Escala Parea Generalizar

PointOnAreaOverlayer_Point (input)
    -> PointOnAreaOverlayer [POINT]
PointOnAreaOverlayer_Area (input)
    -> PointOnAreaOverlayer [AREA]
PointOnAreaOverlayer
    DEAGGREGATE_INPUT = Yes
    OV_ATTR = _overlaps
    POLYS_FIRST = NO
    POINT -> Tester_6
Tester_6
    BOOL_OP = COMPOSITE
    COMPOSITE_TEST = 1 AND ( 2 OR 3 OR 4 OR 5 OR ( 6 AND 7 ) )
    TEST_CLAUSE:
      TEST @Value(fme_feature_type_origem) = edgv.constr_edificacao_p
      TEST @Value(tipo_code) = 2426
      TEST @Value(tipo_code) = 2498
      TEST @Value(tipo_code) = 2501
      TEST @Value(tipo_code) = 2502
      TEST @Value(tipo_code) = 0
      TEST @Value(_overlaps) = 0
    TEST_MODE = TEST
    PASSED -> Tester_8
Tester_8
    BOOL_OP = OR
    TEST_CLAUSE = TEST @Value(tipo_code) = 0
    TEST_MODE = TEST
    PASSED -> GeometryExtractor
    FAILED -> Edif_outras (output)
GeometryExtractor
    ATTR = _geometry
    KIND = fmebinary
    REMOVE_GEOMETRY = No
    KIND_LONG = FME Binary
    -> Bufferer
Bufferer
    ANGLE = 22.5
    CAP_STYLE_LOOKUP = CAP_ARC
    CORNER_STYLE_LOOKUP = JOIN_ARC
    MODE = AREA
    OFFSET = FME_CONDITIONAL:DEFAULT_VALUE'10'BOOL_OP;OR;COMPOSITE_TEST;1;TEST @Value(_escala_parea_generalizar) = 100'20'BOOL_OP;OR;COMPOSITE_TEST;1;TEST @Value(_escala_parea_generalizar) = 250'50'FME_NUM_CONDITIONS3___
    OFFSET_UNITS = METERS
    PRECISION = APPROX
    CAP_STYLE = Arc
    CORNER_STYLE = Arc
    BUFFERED -> Dissolver
Dissolver
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> GeometryReplacer
GeometryReplacer
    KIND = fmebinary
    REMOVE_ATTRIBUTE = Yes
    SOURCE = @Value(_geometry)
    KIND_LONG = FME Binary
    -> Eif_Genereicas_Filtradas (output)
Eif_Genereicas_Filtradas (output)
Edif_outras (output)

FME custom transformer Generalizar_area

Parameters:
- ADMINISTRACAO_CODE = @Value(administracao_code)   # Administracao Code
- ADMINISTRACAO_VALUE = @Value(administracao_value)   # Administracao Value
- ALTITUDE = @Value(altitude)   # altitude
- ALTITUDE_GEOMETRICA = @Value(altitude_geometrica)   # Altitude Geometrica
- ALTITUDE_ORTOMETRICA = @Value(altitude_ortometrica)   # Altitude Ortometrica
- ALTURA = @Value(altura)   # altura
- ANCORA_HORIZONTAL_CODE = @Value(ancora_horizontal_code)   # Ancora Horizontal Code
- ANCORA_HORIZONTAL_VALUE = @Value(ancora_horizontal_value)   # Ancora Horizontal Value
- ANCORA_VERTICAL_CODE = @Value(ancora_vertical_code)   # Ancora Vertical Code
- ANCORA_VERTICAL_VALUE = @Value(ancora_vertical_value)   # Ancora Vertical Value
- ASSENTAMENTO_PRECARIO_CODE = @Value(assentamento_precario_code)   # Assentamento Precario Code
- ASSENTAMENTO_PRECARIO_VALUE = @Value(assentamento_precario_value)   # Assentamento Precario Value
- BITOLA_CODE = @Value(bitola_code)   # Bitola Code
- BITOLA_VALUE = @Value(bitola_value)   # Bitola Value
- CANTEIRO_DIVISORIO_CODE = @Value(canteiro_divisorio_code)   # Canteiro Divisorio Code
- CANTEIRO_DIVISORIO_VALUE = @Value(canteiro_divisorio_value)   # Canteiro Divisorio Value
- COD_PONTO = @Value(cod_ponto)   # Cod Ponto
- CONCESSIONARIA = @Value(concessionaria)   # concessionaria
- CONFIG_COMPRIMENTO_SIMB_CODE = @Value(config_comprimento_simb_code)   # Config Comprimento Simb Code
- CONFIG_COMPRIMENTO_SIMB_VALUE = @Value(config_comprimento_simb_value)   # Config Comprimento Simb Value
- COR = @Value(cor)   # cor
- CORRIGIDO_CODE = @Value(corrigido_code)   # Corrigido Code
- CORRIGIDO_VALUE = @Value(corrigido_value)   # Corrigido Value
- COTA = @Value(cota)   # cota
- COTA_COMPROVADA_CODE = @Value(cota_comprovada_code)   # Cota Comprovada Code
- COTA_COMPROVADA_VALUE = @Value(cota_comprovada_value)   # Cota Comprovada Value
- COTA_MAIS_ALTA_CODE = @Value(cota_mais_alta_code)   # Cota Mais Alta Code
- COTA_MAIS_ALTA_VALUE = @Value(cota_mais_alta_value)   # Cota Mais Alta Value
- DENTRO_MASSA_DAGUA_CODE = @Value(dentro_massa_dagua_code)   # Dentro Massa Dagua Code
- DENTRO_MASSA_DAGUA_VALUE = @Value(dentro_massa_dagua_value)   # Dentro Massa Dagua Value
- DEPRESSAO_CODE = @Value(depressao_code)   # Depressao Code
- DEPRESSAO_VALUE = @Value(depressao_value)   # Depressao Value
- DESCRICAO = @Value(descricao)   # descricao
- DESLOC = @Value(desloc)   # desloc
- DIRECAO = @Value(direcao)   # direcao
- DIRECAO_FIXADA_CODE = @Value(direcao_fixada_code)   # Direcao Fixada Code
- DIRECAO_FIXADA_VALUE = @Value(direcao_fixada_value)   # Direcao Fixada Value
- ELETRIFICADA_CODE = @Value(eletrificada_code)   # Eletrificada Code
- ELETRIFICADA_VALUE = @Value(eletrificada_value)   # Eletrificada Value
- EM_ARRUAMENTO_CODE = @Value(em_arruamento_code)   # Em Arruamento Code
- EM_ARRUAMENTO_VALUE = @Value(em_arruamento_value)   # Em Arruamento Value
- EM_GALERIA_BUEIRO_CODE = @Value(em_galeria_bueiro_code)   # Em Galeria Bueiro Code
- EM_GALERIA_BUEIRO_VALUE = @Value(em_galeria_bueiro_value)   # Em Galeria Bueiro Value
- ESCALA = @Value(escala)   # escala
- ESPACAMENTO = @Value(espacamento)   # espacamento
- ESTILO_FONTE = @Value(estilo_fonte)   # Estilo Fonte
- EXIBIR_LADO_SIMBOLOGIA_CODE = @Value(exibir_lado_simbologia_code)   # Exibir Lado Simbologia Code
- EXIBIR_LADO_SIMBOLOGIA_VALUE = @Value(exibir_lado_simbologia_value)   # Exibir Lado Simbologia Value
- EXIBIR_LINHA_ROTULO_CODE = @Value(exibir_linha_rotulo_code)   # Exibir Linha Rotulo Code
- EXIBIR_LINHA_ROTULO_VALUE = @Value(exibir_linha_rotulo_value)   # Exibir Linha Rotulo Value
- EXIBIR_PONTA_SIMBOLOGIA_CODE = @Value(exibir_ponta_simbologia_code)   # Exibir Ponta Simbologia Code
- EXIBIR_PONTA_SIMBOLOGIA_VALUE = @Value(exibir_ponta_simbologia_value)   # Exibir Ponta Simbologia Value
- EXIBIR_ROTULO_APROXIMADO_CODE = @Value(exibir_rotulo_aproximado_code)   # Exibir Rotulo Aproximado Code
- EXIBIR_ROTULO_APROXIMADO_VALUE = @Value(exibir_rotulo_aproximado_value)   # Exibir Rotulo Aproximado Value
- FINALIDADE_CODE = @Value(finalidade_code)   # Finalidade Code
- FINALIDADE_VALUE = @Value(finalidade_value)   # Finalidade Value
- FME_FEATURE_TYPE = @Value(fme_feature_type)   # Fme Feature Type
- FME_FEATURE_TYPE_ORIGEM = @Value(fme_feature_type_origem)   # Fme Feature Type Origem
- FORMA_EXTRACAO_CODE = @Value(forma_extracao_code)   # Forma Extracao Code
- FORMA_EXTRACAO_VALUE = @Value(forma_extracao_value)   # Forma Extracao Value
- GEOM_TEXTO = @Value(geom_texto)   # Geom Texto
- GEOMETRIA_APROXIMADA_CODE = @Value(geometria_aproximada_code)   # Geometria Aproximada Code
- GEOMETRIA_APROXIMADA_VALUE = @Value(geometria_aproximada_value)   # Geometria Aproximada Value
- ID = @Value(id)   # id
- INDICE_CODE = @Value(indice_code)   # Indice Code
- INDICE_VALUE = @Value(indice_value)   # Indice Value
- INOM = @Value(inom)   # inom
- JURISDICAO_CODE = @Value(jurisdicao_code)   # Jurisdicao Code
- JURISDICAO_VALUE = @Value(jurisdicao_value)   # Jurisdicao Value
- JUSTIFICATIVA = @Value(justificativa)   # justificativa
- JUSTIFICATIVA_TXT_CODE = @Value(justificativa_txt_code)   # Justificativa Txt Code
- JUSTIFICATIVA_TXT_VALUE = @Value(justificativa_txt_value)   # Justificativa Txt Value
- LABEL_X = @Value(label_x)   # Label X
- LABEL_Y = @Value(label_y)   # Label Y
- LARGURA_SIMBOLOGIA = @Value(largura_simbologia)   # Largura Simbologia
- LATITUDE = @Value(latitude)   # latitude
- LONGITUDE = @Value(longitude)   # longitude
- MATERIAL_CONSTRUCAO_CODE = @Value(material_construcao_code)   # Material Construcao Code
- MATERIAL_CONSTRUCAO_ELEMENTO_VIARIO_CODE = @Value(material_construcao_elemento_viario_code)   # Material Construcao Elemento Viario Code
- MATERIAL_CONSTRUCAO_ELEMENTO_VIARIO_VALUE = @Value(material_construcao_elemento_viario_value)   # Material Construcao Elemento Viario Value
- MATERIAL_CONSTRUCAO_VALUE = @Value(material_construcao_value)   # Material Construcao Value
- MI = @Value(mi)   # mi
- MODAL_USO_CODE = @Value(modal_uso_code)   # Modal Uso Code
- MODAL_USO_VALUE = @Value(modal_uso_value)   # Modal Uso Value
- NOME = @Value(nome)   # nome
- NOME_ELEMENTO_VIARIO = @Value(nome_elemento_viario)   # Nome Elemento Viario
- NR_FAIXAS = @Value(nr_faixas)   # Nr Faixas
- NR_LINHAS_CODE = @Value(nr_linhas_code)   # Nr Linhas Code
- NR_LINHAS_VALUE = @Value(nr_linhas_value)   # Nr Linhas Value
- NR_PISTAS = @Value(nr_pistas)   # Nr Pistas
- NUMERO = @Value(numero)   # numero
- OBSERVACAO = @Value(observacao)   # observacao
- ORDEM_SIMBOLOGIA = @Value(ordem_simbologia)   # Ordem Simbologia
- ORGAO_RESPONSAVEL = @Value(orgao_responsavel)   # Orgao Responsavel
- POPULACAO = @Value(populacao)   # populacao
- POSICAO_PISTA_CODE = @Value(posicao_pista_code)   # Posicao Pista Code
- POSICAO_PISTA_ELEMENTO_VIARIO_CODE = @Value(posicao_pista_elemento_viario_code)   # Posicao Pista Elemento Viario Code
- POSICAO_PISTA_ELEMENTO_VIARIO_VALUE = @Value(posicao_pista_elemento_viario_value)   # Posicao Pista Elemento Viario Value
- POSICAO_PISTA_VALUE = @Value(posicao_pista_value)   # Posicao Pista Value
- POSICAO_RELATIVA_CODE = @Value(posicao_relativa_code)   # Posicao Relativa Code
- POSICAO_RELATIVA_VALUE = @Value(posicao_relativa_value)   # Posicao Relativa Value
- POSICAO_ROTULO_CODE = @Value(posicao_rotulo_code)   # Posicao Rotulo Code
- POSICAO_ROTULO_VALUE = @Value(posicao_rotulo_value)   # Posicao Rotulo Value
- REFERENCIAL_ALTIM_CODE = @Value(referencial_altim_code)   # Referencial Altim Code
- REFERENCIAL_ALTIM_VALUE = @Value(referencial_altim_value)   # Referencial Altim Value
- REFERENCIAL_GRAV_CODE = @Value(referencial_grav_code)   # Referencial Grav Code
- REFERENCIAL_GRAV_VALUE = @Value(referencial_grav_value)   # Referencial Grav Value
- REGIME_CODE = @Value(regime_code)   # Regime Code
- REGIME_VALUE = @Value(regime_value)   # Regime Value
- REVESTIMENTO_CODE = @Value(revestimento_code)   # Revestimento Code
- REVESTIMENTO_VALUE = @Value(revestimento_value)   # Revestimento Value
- SIGLA = @Value(sigla)   # sigla
- SIGLA_CODE = @Value(sigla_code)   # Sigla Code
- SIGLA_VALUE = @Value(sigla_value)   # Sigla Value
- SIMB_ROT = @Value(simb_rot)   # Simb Rot
- SISTEMA_GEODESICO_CODE = @Value(sistema_geodesico_code)   # Sistema Geodesico Code
- SISTEMA_GEODESICO_VALUE = @Value(sistema_geodesico_value)   # Sistema Geodesico Value
- SITUACAO_EM_POLIGONO_CODE = @Value(situacao_em_poligono_code)   # Situacao Em Poligono Code
- SITUACAO_EM_POLIGONO_VALUE = @Value(situacao_em_poligono_value)   # Situacao Em Poligono Value
- SITUACAO_FISICA_CODE = @Value(situacao_fisica_code)   # Situacao Fisica Code
- SITUACAO_FISICA_VALUE = @Value(situacao_fisica_value)   # Situacao Fisica Value
- SITUACAO_MARCO_CODE = @Value(situacao_marco_code)   # Situacao Marco Code
- SITUACAO_MARCO_VALUE = @Value(situacao_marco_value)   # Situacao Marco Value
- SOBREPOSTO_CODE = @Value(sobreposto_code)   # Sobreposto Code
- SOBREPOSTO_TRANSPORTES_CODE = @Value(sobreposto_transportes_code)   # Sobreposto Transportes Code
- SOBREPOSTO_TRANSPORTES_VALUE = @Value(sobreposto_transportes_value)   # Sobreposto Transportes Value
- SOBREPOSTO_VALUE = @Value(sobreposto_value)   # Sobreposto Value
- SUBFASE_ID = @Value(subfase_id)   # Subfase Id
- SUJEITO_INUNDACAO_CODE = @Value(sujeito_inundacao_code)   # Sujeito Inundacao Code
- SUJEITO_INUNDACAO_VALUE = @Value(sujeito_inundacao_value)   # Sujeito Inundacao Value
- SUPRIMIR_BANDEIRA_CODE = @Value(suprimir_bandeira_code)   # Suprimir Bandeira Code
- SUPRIMIR_BANDEIRA_VALUE = @Value(suprimir_bandeira_value)   # Suprimir Bandeira Value
- SUPRIMIR_SIMBOLOGIA_CODE = @Value(suprimir_simbologia_code)   # Suprimir Simbologia Code
- SUPRIMIR_SIMBOLOGIA_VALUE = @Value(suprimir_simbologia_value)   # Suprimir Simbologia Value
- TAMANHO_TXT = @Value(tamanho_txt)   # Tamanho Txt
- TEXTO_EDICAO = @Value(texto_edicao)   # Texto Edicao
- TIPO_CODE = @Value(tipo_code)   # Tipo Code
- TIPO_ELEMENTO_VIARIO_CODE = @Value(tipo_elemento_viario_code)   # Tipo Elemento Viario Code
- TIPO_ELEMENTO_VIARIO_VALUE = @Value(tipo_elemento_viario_value)   # Tipo Elemento Viario Value
- TIPO_EXPOSICAO_CODE = @Value(tipo_exposicao_code)   # Tipo Exposicao Code
- TIPO_EXPOSICAO_VALUE = @Value(tipo_exposicao_value)   # Tipo Exposicao Value
- TIPO_GRID = @Value(tipo_grid)   # Tipo Grid
- TIPO_PRODUTO_CODE = @Value(tipo_produto_code)   # Tipo Produto Code
- TIPO_PRODUTO_VALUE = @Value(tipo_produto_value)   # Tipo Produto Value
- TIPO_REF_CODE = @Value(tipo_ref_code)   # Tipo Ref Code
- TIPO_REF_VALUE = @Value(tipo_ref_value)   # Tipo Ref Value
- TIPO_VALUE = @Value(tipo_value)   # Tipo Value
- TRAFEGO_CODE = @Value(trafego_code)   # Trafego Code
- TRAFEGO_VALUE = @Value(trafego_value)   # Trafego Value
- USO_PISTA_CODE = @Value(uso_pista_code)   # Uso Pista Code
- USO_PISTA_VALUE = @Value(uso_pista_value)   # Uso Pista Value
- VISIVEL_CODE = @Value(visivel_code)   # Visivel Code
- VISIVEL_VALUE = @Value(visivel_value)   # Visivel Value
- AREA_MINIMA_VALOR = @Value(area_minima_valor)   # Area Minima Valor

Dissolver_Input (input)
    -> Dissolver
Dissolver
    ACCUM_INPUT_ATTRS = Use Attributes From One Feature
    CLEANING_TOLERANCE_LOOKUP = AUTO
    CONNECT_Z_MODE_LOOKUP = FIRST_WINS
    DEAGGREGATE_INPUT = Yes
    GROUP_BY = fme_feature_type_origem tipo_code
    CLEANING_TOLERANCE = Automatic
    CONNECT_Z_MODE = First Wins
    AREA -> AttributeCreator
AttributeCreator
    ATTR_TABLE = SET_TO area (varchar(200)) = @Area()
    -> Tester_2
Tester_2
    BOOL_OP = OR
    TEST_CLAUSE = TEST @Value(area) >= @Value(area_minima_valor)
    TEST_MODE = TEST
    PASSED -> Junction
    FAILED -> Dissolver_2
Dissolver_2
    ACCUM_INPUT_ATTRS = Use Attributes From One Feature
    CLEANING_TOLERANCE_LOOKUP = AUTO
    CONNECT_Z_MODE_LOOKUP = FIRST_WINS
    DEAGGREGATE_INPUT = Yes
    CLEANING_TOLERANCE = Automatic
    CONNECT_Z_MODE = First Wins
    AREA -> Tester_3
Tester_3
    BOOL_OP = OR
    TEST_CLAUSE = TEST @Value(area) >= @Value(area_minima_valor)
    TEST_MODE = TEST
    PASSED -> Junction
    FAILED -> NeighborFinder [BASE]
Junction
    -> NeighborFinder [CANDIDATE]
    -> AttributeCreator_2
AttributeCreator_2
    ATTR_TABLE = SET_TO id_merge (varchar(200)) = @Value(id)
    -> FeatureMerger [SUPPLIER]
    -> Junction_2
NeighborFinder
    CANDIDATES_FIRST = No
    CLOSE_LIST_ATTRS_TO_INCLUDE = area fme_feature_type fme_feature_type_origem id tipo_code
    CLOSE_LIST_ATTRS_TO_INCLUDE_MODE = Selected Attributes
    CLOSE_LIST_NAME = merge
    INSERT_VERTEX = No
    K = 4
    MAX = 1
    MEASURES_FROM_CANDIDATE = Yes
    MEASURE_TYPE = Continuous
    MODE = Bases and Candidates
    TREAT_POLYGON_AS = Lines
    MATCHED -> PythonCaller_2
    UNMATCHED_BASE -> NeighborFinder_UnmatchedBase (output)
PythonCaller_2
    NEW_ATTRIBUTES = id_merge varchar(200) area_merge real32
    PYTHONSOURCE:
      import fme
      import fmeobjects

      class FeatureProcessor(object):
          """Template Class Interface:
          When using this class, make sure its name is set as the value of the 'Class to Process Features'
          transformer parameter.
          """

          def __init__(self):
              """Base constructor for class members."""
              pass

          def has_support_for(self, support_type: int):
              """This method is called by FME to determine if the PythonCaller supports Bulk mode,
              which allows for significant performance gains when processing large numbers of features.
              Bulk mode cannot always be supported.
              More information available in transformer help.
              """
              return support_type == fmeobjects.FME_SUPPORT_FEATURE_TABLE_SHIM

          def input(self, feature: fmeobjects.FMEFeature):
              """This method is called for each feature which enters the PythonCaller.
              Processed input features can be emitted from this method using self.pyoutput().
              If knowledge of all input features is required for processing, then input features should be
              cached to a list instance variable and processed using group processing or in the close() method.
              """

              # Substitua pelo nome real do seu atributo de entrada
              range = []
              if(feature.getAttribute('merge{0}.area')):
                 range.append([ feature.getAttribute('merge{0}.id'), feature.getAttribute('merge{0}.area') ])
              if(feature.getAttribute('merge{1}.area')):
                 range.append([ feature.getAttribute('merge{1}.id'), feature.getAttribute('merge{1}.area') ])
              if(feature.getAttribute('merge{2}.area')):
                 range.append([ feature.getAttribute('merge{2}.id'), feature.getAttribute('merge{2}.area') ])
              if(feature.getAttribute('merge{3}.area')):
                 range.append([ feature.getAttribute('merge{3}.id'), feature.getAttribute('merge{3}.area') ])

              id_merge = None
              area_merge = 0
              for r in range:
                  if(r[1] > area_merge):
                      area_merge = r[1]
                      id_merge = r[0]

              feature.setAttribute("id_merge", id_merge)
              feature.setAttribute("area_merge", area_merge)

              self.pyoutput(feature)

          def close(self):
              """This method is called once all the FME Features have been processed from input()."""
              pass

          def process_group(self):
              """This method is called by FME for each group when group processing mode is enabled.
              This implementation should reset any instance variables used for the next group.
              Bulk mode should not be enabled when using group processing.
              More information available in transformer help.
              """
              pass
    PYTHONSYMBOL = FeatureProcessor
    -> Junction_2
Junction_2
    -> Dissolver_3
Dissolver_3
    ACCUM_INPUT_ATTRS = Drop Incoming Attributes
    CLEANING_TOLERANCE_LOOKUP = AUTO
    CONNECT_Z_MODE_LOOKUP = FIRST_WINS
    DEAGGREGATE_INPUT = Yes
    GROUP_BY = id_merge
    CLEANING_TOLERANCE = Automatic
    CONNECT_Z_MODE = First Wins
    AREA -> FeatureMerger [REQUESTOR]
FeatureMerger
    ATTR_ACCUM_MODE = Merge Supplier
    ATTR_CONFLICT_RES_LOOKUP = REQUESTOR_IF_CONFLICT
    IGNORE_NULLS = No
    JOIN_KEYS = @Value(id_merge) @Value(id_merge) AUTO
    MERGE_TYPE = Attributes Only
    PROCESS_DUPS = NO
    REJECT_NULL_MISSING_KEYS = No
    SUPPLIERS_FIRST = No
    ATTR_CONFLICT_RES = Use Requestor
    MERGED -> FeatureMerger_Merged (output)
FeatureMerger_Merged (output)
NeighborFinder_UnmatchedBase (output)

FME custom transformer Remover_linhas_soltas

Intersector_Input (input)
    -> Intersector
    -> PointOnLineOverlayer_2 [LINE]
Intersector
    ATTRS_ACCUM_MODE = Use Attributes From One Feature
    CLEANING_TOLERANCE_LOOKUP = AUTO
    DEAGGREGATE_INPUT = Yes
    DIRECTION_NAME = _direction
    GENERATE_LIST_DROP = NO
    IGNORE_HEIGHTS = YES
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    INTERSECTED -> PointOnLineOverlayer [LINE]
    NODE -> PointOnLineOverlayer [POINT]
PointOnLineOverlayer
    DEAGGREGATE_INPUT = Yes
    MEASURE_TYPE_LOOKUP = CONTINUOUS
    MERGE_MEASURES = Yes
    OV_ATTR = _overlaps
    TOLERANCE = 1
    MEASURE_TYPE = Continuous
    POINT -> Tester_4
Tester_4
    BOOL_OP = OR
    TEST_CLAUSE = TEST @Value(_overlaps) > 1
    TEST_MODE = TEST
    PASSED -> PointOnLineOverlayer_2 [POINT]
PointOnLineOverlayer_2
    DEAGGREGATE_INPUT = Yes
    MEASURE_TYPE_LOOKUP = CONTINUOUS
    MERGE_MEASURES = Yes
    OV_ATTR = _overlaps
    TOLERANCE = 1
    MEASURE_TYPE = Continuous
    LINE -> Tester
Tester
    BOOL_OP = OR
    TEST_CLAUSE = TEST @Value(_overlaps) > 1
    TEST_MODE = TEST
    PASSED -> Tester_Passed (output)
Tester_Passed (output)

FME custom transformer Filtrar_cotas

Parameters:
- COTA = @Value(cota)   # cota
- ID = @Value(id)   # id
- ID_CELULAR_GRID = @Value(id_celular_grid)   # Id Celular Grid

PointOnAreaOverlayer_2_Point (input)
    -> PointOnAreaOverlayer_2 [POINT]
AttributeKeeper_19_Input (input)
    -> AttributeKeeper_19
AttributeKeeper_19
    CREATE_BULK_MODE_FEATURES = NO
    KEEP_ATTRS = id_celular_grid
    -> PointOnAreaOverlayer_2 [AREA]
PointOnAreaOverlayer_2
    ATTR_ACCUM_MODE = Merge Incoming
    ATTR_CONFLICT_RES_LOOKUP = ORIGINAL_IF_CONFLICT
    CANDIDATE_LIST_ATTRS_TO_INCLUDE = cota id
    CANDIDATE_LIST_ATTRS_TO_INCLUDE_MODE_LU = SELECTED
    CANDIDATE_LIST_NAME = pontos_cotados
    DEAGGREGATE_INPUT = Yes
    OV_ATTR = qtd_cotas_agregadas
    POLYS_FIRST = NO
    ATTR_CONFLICT_RES = Use Original
    CANDIDATE_LIST_ATTRS_TO_INCLUDE_MODE = Selected Attributes
    POINT -> Sorter_4
Sorter_4
    GROUP_BY = id_celular_grid
    SORT_PARM = cota NUMERIC DESCENDING
    SORTED -> ModuloCounter_3
ModuloCounter_3
    CNT_ATTR = _modulo_count
    DOMAIN = @Value(id_celular_grid)
    MOD = 1000
    -> AttributeCreator_20
AttributeCreator_20
    ATTR_TABLE = SET_TO visivel (varchar(200)) = FME_CONDITIONAL:DEFAULT_VALUE'2'BOOL_OP;OR;COMPOSITE_TEST;1;TEST @Value(_modulo_count) <= 3'1'FME_NUM_CONDITIONS2___
    -> Tester_6
Tester_6
    BOOL_OP = OR
    TEST_CLAUSE = TEST @Value(visivel) = 1
    TEST_MODE = TEST
    PASSED -> Tester_6_Passed (output)
Tester_6_Passed (output)
