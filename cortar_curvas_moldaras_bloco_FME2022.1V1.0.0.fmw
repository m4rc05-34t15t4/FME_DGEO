FME workspace cortar_curvas_moldaras_bloco_FME2022.1V1.0.0.fmw

Parameters:
- SourceDataset_POSTGIS = curvas_bloco_a   # Database
- SourceDataset_POSTGIS_3 = bloco_a   # Database
- DestDataset_OGCGEOPACKAGE = $(FME_MF_DIR)Gerar_flags_occorutos_sem_pt_cotado\Bloco_A\curvas_A_cortadas.gpkg   # GeoPackage File

Readers:
- POSTGIS_1: POSTGIS from $(SourceDataset_POSTGIS)
- POSTGIS_2: POSTGIS from $(SourceDataset_POSTGIS_3)

Writers:
- OGCGEOPACKAGE_1: OGCGEOPACKAGE to $(DestDataset_OGCGEOPACKAGE)

aux_moldura_a (reader POSTGIS_2)
    attributes: id serial, escala varchar(255), inom varchar(255), mi varchar(255), nome varchar(80)
    -> edgv.aux_moldura_a
    -> Clipper [CLIPPER]
edgv.aux_moldura_a: Inspector [off]
rel_curva_nivel_l (reader POSTGIS_1)
    attributes: id serial, geometriaaproximada bool, cota int4, depressao bool, tipocurvanivel int2
    -> edgv.rel_curva_nivel_l
    -> Clipper [CANDIDATE]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> GeometryExtractor
    OUTSIDE -> GeometryExtractor
GeometryExtractor
    ATTR = _geometry
    KIND_LONG = OGC Well Known Text
    OGCVERSION = 1.2
    OGC_WKT_PRECISION_DISPLAY = 64-bit
    REMOVE_GEOMETRY = No
    -> GeometryReplacer
GeometryReplacer
    KIND_LONG = OGC Well Known Text
    OGC_WKT_PRECISION_DISPLAY = 64-bit
    REMOVE_ATTRIBUTE = Yes
    SOURCE = @Value(_geometry)
    -> AttributeKeeper
AttributeKeeper
    CREATE_BULK_MODE_FEATURES = NO
    KEEP_ATTRS = cota,depressao,geometriaaproximada,id,tipocurvanivel
    -> rel_curva_nivel_l (writer OGCGEOPACKAGE_1)
rel_curva_nivel_l (writer OGCGEOPACKAGE_1)
    attributes: id mediumint, geometriaaproximada boolean, cota mediumint, depressao boolean, tipocurvanivel smallint
edgv.rel_curva_nivel_l: Inspector [off]
