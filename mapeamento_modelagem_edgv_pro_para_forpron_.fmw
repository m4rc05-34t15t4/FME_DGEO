FME workspace mapeamento_modelagem_edgv_pro_para_forpron_.fmw

Parameters:
- SourceDataset_OGCGEOPACKAGE = C:\Marcos_Batista\DGEO\FORPRON\Forpron_2025\Area_conversao.gpkg   # GeoPackage File
- FEATURE_TYPES_2 =
- DestDataset_POSTGIS = combater_2025   # Database
- SourceDataset_POSTGIS = pit_topo_pe_2025_50k   # Database
- FEATURE_TYPES = edgv.aux_moldura_a edgv.aux_moldura_area_continua_a edgv.aux_observacao_a edgv.aux_observacao_l edgv.aux_observacao_p edgv.aux_reambulacao_a edgv.aux_reambulacao_l edgv.aux_reambulacao_p edgv.aux_revisao_a edgv.aux_revisao_l edgv.aux_revisao_p edgv.centroide_area_edificada_p edgv.centroide_area_sem_dados_p edgv.centroide_elemento_hidrografico_p edgv.centroide_ilha_p edgv.centroide_limite_especial_p edgv.centroide_massa_dagua_p edgv.centroide_vegetacao_p edgv.cobter_area_construida_a edgv.cobter_area_edificada_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_edificada_l edgv.delimitador_area_sem_dados_l edgv.delimitador_elemento_hidrografico_l edgv.delimitador_limite_especial_l edgv.delimitador_massa_dagua_l edgv.delimitador_vegetacao_l edgv.edicao_borda_elemento_hidrografico_l edgv.edicao_grid_edicao_l edgv.edicao_grid_numerico_p edgv.edicao_identificador_trecho_rod_p edgv.edicao_limite_especial_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_toponimo_fisiografico_natural_l edgv.elemnat_toponimo_fisiografico_natural_p edgv.elemnat_trecho_drenagem_l edgv.infra_alteracao_fisiografica_antropica_a edgv.infra_alteracao_fisiografica_antropica_l edgv.infra_barragem_a edgv.infra_barragem_l edgv.infra_barragem_p edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_mobilidade_urbana_l edgv.infra_obstaculo_vertical_p edgv.infra_pista_pouso_a edgv.infra_pista_pouso_l edgv.infra_pista_pouso_p edgv.infra_travessia_hidroviaria_l edgv.infra_travessia_hidroviaria_p edgv.infra_trecho_duto_l edgv.infra_trecho_hidroviario_l edgv.infra_vala_l edgv.infra_via_deslocamento_l edgv.llp_area_sem_dados_a edgv.llp_delimitacao_fisica_l edgv.llp_limite_especial_a edgv.llp_limite_legal_l edgv.llp_localidade_p edgv.llp_pais_a edgv.llp_ponto_controle_p edgv.llp_unidade_federacao_a

Readers:
- OGCGEOPACKAGE_1: OGCGEOPACKAGE from $(SourceDataset_OGCGEOPACKAGE)
- POSTGIS_1: POSTGIS from $(SourceDataset_POSTGIS)

Writers:
- POSTGIS_2: POSTGIS to $(DestDataset_POSTGIS)

Note: : area_recorte_mapeamento_pe [OGCGEOPACKAGE]
area_recorte_mapeamento_pe (reader OGCGEOPACKAGE_1)
    attributes: id mediumint, mi text(10), carta_nome text(40), aq_respvl text(15), aq_ini date, aq_fim date, val_respvl text(15), val_ini date, val_fim date, area_cont_respvl text(15), area_cont_ini date, area_cont_fim date, ed_respvl text(15), ed_ini date, ed_fim date, fid int,PrimaryKey
    -> Clipper [CLIPPER]
Note: : pit_topo_pe_2025_50k [POSTGIS]
aux_moldura_a (reader POSTGIS_1)
    attributes: id uuid, nome varchar(255), mi varchar(255), inom varchar(255), observacao varchar(255), operador_criacao varchar(255), data_criacao timestamptz, operador_atualizacao varchar(255), data_atualizacao timestamptz, administracao int2, altitude float4, altitude_geometrica varchar(255), altitude_ortometrica varchar(255), altura float4, ancora_horizontal int2, ancora_vertical int2, assentamento_precario int2, atividade_id int4, bitola int2, canteiro_divisorio int2, cod_ponto varchar(255), concessionaria varchar(255), config_comprimento_simb int2, cor varchar(255), corrigido int2, cota int4, cota_comprovada int2, cota_mais_alta int2, creation_time timestamptz, data_fim timestamptz,
      data_importacao timestamp, data_inicio timestamptz, data_track date, densamente_edificada int2, dentro_massa_dagua int2, depressao int2, descricao varchar(255), desloc float4, direcao varchar(255), direcao_fixada int2, eletrificada int2, elevation float4, em_arruamento int2, em_galeria_bueiro int2, espacamento float4, estilo_fonte varchar(255), etapa_id int4, exibir_lado_simbologia int2, exibir_linha_rotulo int2, exibir_ponta_simbologia int2, exibir_rotulo_aproximado int2, finalidade int2, forma_extracao int2, geometria_aproximada int2, indice int2, json_atividade text, jurisdicao int2, justificativa varchar(255), justificativa_txt int2, label_x float4,
      label_y float4, largura_simbologia float4, latitude varchar(255), longitude varchar(255), material_construcao int2, material_construcao_elemento_viario int2, max_t timestamptz, min_t timestamptz, modal_uso int2, nome_elemento_viario varchar(255), nome_usuario varchar(255), nr_faixas varchar(255), nr_linhas int2, nr_pistas varchar(255), numero varchar(255), operador text, ordem_simbologia int4, orgao_responsavel varchar(255), populacao int4, posicao_pista int2, posicao_pista_elemento_viario int2, posicao_relativa int2, posicao_rotulo int2, rank int4, referencial_altim int2, referencial_grav int2, regime int2, revestimento int2, sigla varchar(255), simb_rot float4,
      sistema_geodesico int2, situacao_em_poligono int2, situacao_fisica int2, situacao_marco int2, sobreposto int2, sobreposto_transportes int2, subfase_id int4, sujeito_inundacao int2, suprimir_bandeira int2, suprimir_simbologia int2, tamanho_txt float4, texto_edicao varchar(255), tipo int2, tipo_elemento_viario int2, tipo_exposicao int2, tipo_grid varchar(255), tipo_produto int2, tipo_ref int2, track_id text, track_segment int4, track_segment_point_index int4, trafego int2, unidade_trabalho_id int4, uso_pista int2, usuario_uuid uuid, visited bool, visivel int2, vtr text, x_ll float4, y_ll float4
    -> AttributeFilter
AttributeFilter
    ATTR_NAME = fme_feature_type
    ATTR_VALUES = <Empty>,<Missing>,<Null>,<Unfiltered>,edgv.cobter_massa_dagua_a,edgv.elemnat_ponto_cotado_p,edgv.elemnat_curva_nivel_l,edgv.infra_ferrovia_l,edgv.elemnat_trecho_drenagem_l,edgv.infra_via_deslocamento_l
    PRESERVE_FEATURE_ORDER_LOOKUP = PER_OUTPUT_PORT
    <UNFILTERED> -> Tester
    edgv.cobter_massa_dagua_a -> AttributeCreator_2
    edgv.elemnat_ponto_cotado_p -> base.ponto_cotado_altimetrico_p
    edgv.elemnat_curva_nivel_l -> base.curva_nivel_l
    edgv.infra_ferrovia_l -> base.ferrovia_l
    edgv.elemnat_trecho_drenagem_l -> base.rio_l
    edgv.infra_via_deslocamento_l -> AttributeFilter_2
Tester
    BOOL_OP = OR
    TEST_CLAUSE = TEST @Right(@Value(fme_feature_type),2) = _a
    TEST_MODE = TEST
    PASSED -> AttributeCreator_3
AttributeCreator_2
    ATTR_TABLE = SET_TO MASSA_CODE = 1004
    -> AttributeCreator_3
AttributeCreator_3
    ATTR_TABLE = SET_TO fme_feature_type = base.cob_ter_a
    -> Junction
base.ponto_cotado_altimetrico_p: AttributeCreator
    ATTR_TABLE = SET_TO fme_feature_type = base.ponto_cotado_altimetrico_p
    -> Junction_2
base.curva_nivel_l: AttributeCreator
    ATTR_TABLE = SET_TO fme_feature_type = base.curva_nivel_l
    -> Junction_2
base.ferrovia_l: AttributeCreator
    ATTR_TABLE = SET_TO fme_feature_type = base.ferrovia_l
    -> Junction_2
AttributeFilter_2
    ATTR_NAME = tipo
    ATTR_VALUES = <Empty>,<Missing>,<Null>,<Unfiltered>,1,2,3,9999
    1 -> base.estrada_l
    2 -> base.estrada_l
    3 -> base.estrada_l
    9999 -> base.estrada_l
base.estrada_l: AttributeCreator
    ATTR_TABLE:
      SET_TO MASACODE = FME_CONDITIONAL:DEFAULT_VALUE'20004'BOOL_OP;COMPOSITE;COMPOSITE_TEST;1 AND ( 2 OR 3 );TEST @Value(tipo) != 3;TEST @Value(jurisdicao) = 1;TEST @Value(jurisdicao) = 2'20002'BOOL_OP;OR;COMPOSITE_TEST;1;TEST @Value(tipo) != 3'20003'FME_NUM_CONDITIONS3___
      SET_TO CAMADAS COMBATER = FME_CONDITIONAL:DEFAULT_VALUE'SMALL_ROAD'BOOL_OP;COMPOSITE;COMPOSITE_TEST;1 AND ( 2 OR 3 );TEST @Value(tipo) != 3;TEST @Value(jurisdicao) = 1;TEST @Value(jurisdicao) = 2'LARGE_ROAD'BOOL_OP;OR;COMPOSITE_TEST;1;TEST @Value(tipo) != 3'MEDIUM_ROAD'FME_NUM_CONDITIONS3___
      SET_TO nome = @Value(sigla)
      SET_TO fme_feature_type = base.estrada_l
    -> Junction_2
base.rio_l: AttributeCreator
    ATTR_TABLE = SET_TO fme_feature_type = base.rio_l
    -> Junction_2
Junction_2
    -> Junction
Junction
    -> Clipper [CANDIDATE]
Clipper
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> AttributeKeeper
    OUTSIDE -> Clipper_Outside
AttributeKeeper
    CREATE_BULK_MODE_FEATURES = NO
    KEEP_ATTRS = id,fme_feature_type,MASSA_CODE,cota,CAMADAS COMBATER,nome
    -> Sorter
Sorter
    GROUP_BY = fme_feature_type
    SORT_PARM = id NUMERIC ASCENDING
    SORTED -> Counter
Counter
    CNT_ATTR = id
    DOMAIN = @Value(fme_feature_type)
    SCOPE = Global
    START = 1
    -> Tester_2
Tester_2
    BOOL_OP = OR
    TEST_CLAUSE = TEST @Value(fme_feature_type) = base.rio_l
    TEST_MODE = TEST
    PASSED -> AggregateFilter
    FAILED -> AttributeCreator_4
AggregateFilter
    PRESERVE_FEATURE_ORDER_LOOKUP = PER_OUTPUT_PORT
    AGGREGATE -> Aggregator_2
    NOT_AGGREGATE -> Aggregator_2
Aggregator_2
    ACCUM_ATTRS_NAME = Merge Incoming Attributes
    AGGREGATE_TYPE = Heterogeneous Collection
    GROUP_BY = fme_feature_type id
    MODE = Geometry - Assemble One Level
    SEP = ,
    AGGREGATE -> AttributeCreator_4
AttributeCreator_4
    ATTR_TABLE:
      SET_TO geometriaaproximada = 9999
      SET_TO cotacomprovada = 9999
      SET_TO descricao = MAPEAMENTO_PE
      SET_TO codigo = 1
    -> Table1 (writer POSTGIS_2)
    -> RESULTADO
Note: : Combater_2025 [POSTGIS]
Table1 (writer POSTGIS_2)
RESULTADO: Inspector
    TACKATTRS = fme_feature_type
Clipper_Outside: Inspector
