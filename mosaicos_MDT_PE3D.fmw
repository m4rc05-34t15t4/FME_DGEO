FME workspace mosaicos_MDT_PE3D.fmw

Parameters:
- SourceDataset_GEOTIFF = ""C:\Marcos_Batista\FME\Projeto Pernambuco\Insumos\Curva_B\Geotiff_1_B.tif" "C:\Marcos_Batista\FME\Projeto Pernambuco\Insumos\Curva_B\Geotiff_2_B.tif" "C:\Marcos_Batista\FME\Projeto Pernambuco\Insumos\Curva_B\Geotiff_3_B.tif" "C:\Marcos_Batista\FME\Projeto Pernambuco\Insumos\Curva_B\Geotiff_4_B.tif""   # Source GeoTIFF File(s)
- DestDataset_GEOTIFF = C:\Marcos_Batista\FME\Projeto Pernambuco\Insumos\Curva_B   # Destination GeoTIFF Folder
- EPSG = EPSG:31984

Readers:
- GEOTIFF_1: GEOTIFF from $(SourceDataset_GEOTIFF)

Writers:
- GEOTIFF_2: GEOTIFF to $(DestDataset_GEOTIFF) in $(EPSG)

GEOTIFF (reader GEOTIFF_1)
    -> Reprojector
Note: reprojeta
Reprojector
    DEST = $(EPSG)
    INTERPOLATION_TYPE_NAME = Nearest Neighbor
    RASTER_CELL_SIZE = Preserve Cells
    RASTER_TOLERANCE = 0.0
    SOURCE = Read from feature
    REPROJECTED -> RasterBandNodataRemover
RasterBandNodataRemover
    -> RasterMosaicker
RasterMosaicker
    ACCUM_ATTRS_NAME = Use Attributes From One Feature
    INTERPOLATION_TYPE_NAME = Nearest Neighbor
    MERGE_PALETTES_NAME = No
    OVERLAPPING_VALUES = max
    SNAPPING_TYPE_NAME = Resample
    -> RasterResampler
Note: Modifica o "valor" das celulas
RasterResampler
    INTERPOLATION_TYPE_NAME = Bilinear
    ROWCOL_OR_CELLSIZE = CellSize
    X_CELL_SIZE = 2.5
    Y_CELL_SIZE = 2.5
    RESAMPLED -> GEOTIFF_comprimido2 (writer GEOTIFF_2)
GEOTIFF_comprimido2 (writer GEOTIFF_2)
