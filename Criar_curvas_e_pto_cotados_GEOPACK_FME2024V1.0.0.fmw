FME workspace Criar_curvas_e_pto_cotados_GEOPACK_FME2024V1.0.0.fmw

Parameters:
- MDT_geotiff = C:\Marcos_Batista\DGEO\2025\100K\mosaico.tif   # mdt_geotiff
- EPSG = EPSG:4674
- Equidistancia = 50   # equidistancia
- destino_geopack = C:\Marcos_Batista\DGEO\2025\100K
- SourceDataset_OGCGEOPACKAGE = C:\Marcos_Batista\DGEO\2025\100K\contornos.gpkg   # GeoPackage File
- FEATURE_TYPES_2 =

Readers:
- GEOTIFF_1: GEOTIFF from $(MDT_geotiff)
- OGCGEOPACKAGE_3: OGCGEOPACKAGE from $(SourceDataset_OGCGEOPACKAGE)

Writers:
- OGCGEOPACKAGE_2: OGCGEOPACKAGE to $(destino_geopack)

contornos (reader OGCGEOPACKAGE_3)
    attributes: ID mediumint, cota double, comprimento double, fid int,PrimaryKey
    -> AttributeRenamer_2

Bookmark: Se necessário
AttributeRenamer_2
    ATTR_TABLE = RENAME_SET_DEFAULT ID > id
    -> AttributeCreator_4
AttributeCreator_4
    ATTR_TABLE:
      SET_TO depressao = falso
      SET_TO indice = 2
    -> Reprojector_3
Reprojector_3
    DEST = $(EPSG)
    INTERPOLATION_TYPE = ,NearestNeighbor
    RASTER_CELL_SIZE_LOOKUP = ,PreserveCells
    RASTER_TOLERANCE = 0.0
    SOURCE = Read from feature
    INTERPOLATION_TYPE_NAME = Nearest Neighbor
    RASTER_CELL_SIZE = Preserve Cells
    REPROJECTED -> GeometryFilter

Bookmark: Seleciona as Curvas
GeometryFilter
    BREAK_AGG_BOOL = 0
    GEOM_PORTS = LINE
    BREAK_AGG = No
    GEOM_PORT_NAMES = Line
    LINE -> Tester_4
    <UNFILTERED> -> GeometryFilter__Unfiltered_
GeometryFilter__Unfiltered_: Inspector
Tester_4
    BOOL_OP = OR
    TEST_CLAUSE = TEST @Length() > 90
    TEST_MODE = TEST
    PASSED -> AttributeKeeper
    FAILED -> AttributeKeeper
AttributeKeeper
    CREATE_BULK_MODE_FEATURES = NO
    KEEP_ATTRS = cota,depressao,id,indice
    -> ClosedCurveFilter
    -> Curva
    -> NeighborFinder [CANDIDATE]
    -> Intersector_2
Curva: Inspector

Bookmark: Pontos cotados de Cocoruto
ClosedCurveFilter
    CHECK_NODE_ELEVATION_LOOKUP = CHECK_CLOSURE_3D
    CHECK_NODE_ELEVATION = Yes
    CLOSED -> LineCloser
    OPEN -> Tester_2
LineCloser
    CONNECT_Z_MODE_LOOKUP = FIRST_WINS
    CONNECT_Z_MODE = First Wins
    AREA -> AttributeCreator
Tester_2
    BOOL_OP = AND
    TEST_CLAUSE = TEST @Length() > 100
    TEST_MODE = TEST
    PASSED -> LineCloser_2
LineCloser_2
    CONNECT_Z_MODE_LOOKUP = FIRST_WINS
    CONNECT_Z_MODE = First Wins
    AREA -> GeometryValidator
GeometryValidator
    ISSUE_ATTR_NAME = _issues
    PRESETS = OGC
    REPAIR = Yes
    RULES = OGC_SIMPLE_CHECK  OGC_VALID_CHECK OGC_VERSION]V1.2.0]FME_CONTROLLER_QUERY_FILE]transformers\dependencies\geometryvalidator\OGC_VALID_CHECK.fme
    SUMMARY = Detailed
    PASSED -> Tester_3
Tester_3
    BOOL_OP = OR
    TEST_CLAUSE = TEST @Area() < 35000.00
    TEST_MODE = TEST
    PASSED -> AttributeCreator
AttributeCreator
    ATTR_TABLE = SET_TO Area = @Area()
    -> PointOnAreaOverlayer [AREA]
    -> CenterPointReplacer
CenterPointReplacer
    POINTTYPE = INSIDE
    POINT -> PointOnAreaOverlayer [POINT]
PointOnAreaOverlayer
    CANDIDATE_LIST_ATTRS_TO_INCLUDE = cota id Area
    CANDIDATE_LIST_ATTRS_TO_INCLUDE_MODE_LU = SELECTED
    CANDIDATE_LIST_NAME = pontos
    DEAGGREGATE_INPUT = Yes
    OV_ATTR = _overlaps
    POLYS_FIRST = NO
    CANDIDATE_LIST_ATTRS_TO_INCLUDE_MODE = Selected Attributes
    AREA -> PythonCaller
PythonCaller
    NEW_ATTRIBUTES = Cocoruto
    PYTHONSOURCE:
      import fme
      import fmeobjects

      def processFeature(feature):
          Cocoruto = True
          if(feature.getAttribute('_overlaps') == 1 and (feature.getAttribute('cota') < feature.getAttribute('pontos{0}.cota') or float(feature.getAttribute('Area')) > float(feature.getAttribute('pontos{0}.Area'))) ):
              Cocoruto = False
          elif(feature.getAttribute('_overlaps') > 1):
              i = 0
              while i < len(feature.getAttribute('pontos{}.cota')):
                  if(int(feature.getAttribute('pontos{'+str(i)+'}.cota')) > int(feature.getAttribute('cota')) or float(feature.getAttribute('Area')) > float(feature.getAttribute('pontos{0}.Area'))):
                      Cocoruto = False
                      break
                  i += 1
          #Set Attributes
          feature.setAttribute("Cocoruto", Cocoruto)
    PYTHONSYMBOL = processFeature
    -> Tester
Tester
    BOOL_OP = OR
    TEST_CLAUSE = TEST @Value(Cocoruto) = Yes
    TEST_MODE = TEST
    PASSED -> CenterPointReplacer_2
CenterPointReplacer_2
    POINTTYPE = INSIDE
    POINT -> AttributeKeeper_2
AttributeKeeper_2
    CREATE_BULK_MODE_FEATURES = NO
    KEEP_ATTRS = Area,cota
    -> Cocoruto
    -> Reprojector_2
Cocoruto: Inspector

Bookmark: Pontos cotados de Sela
NeighborFinder
    GROUP_BY = cota
    INSERT_VERTEX = No
    K = 5
    MAX = 1000
    MEASURES_FROM_CANDIDATE = Yes
    MEASURE_TYPE = Continuous
    MODE = Candidates Only
    TREAT_POLYGON_AS = Lines
    MATCHED -> VertexCreator
VertexCreator
    MEASURE_TYPE_LOOKUP = CONTINUOUS
    MODE = REPLACE
    XVAL = @Value(_closest_base_x)
    YVAL = @Value(_closest_base_y)
    ZVAL = @Value(id)
    MEASURE_TYPE = Continuous
    MODE_NAME = Replace with Point
    -> VertexCreator_2
VertexCreator_2
    ALLOW_DUPLICATES = NO
    MEASURE_TYPE_LOOKUP = CONTINUOUS
    MISSING_VAL_MODE_LOOKUP = COMPUTE_NANS
    MODE = ADD
    XVAL = @Value(_closest_candidate_x)
    YVAL = @Value(_closest_candidate_y)
    ZVAL = @Value(cota)
    IGNORE_DUPLICATES = Yes
    MEASURE_TYPE = Continuous
    MISSING_VAL_MODE = Compute
    MODE_NAME = Add Point
    -> Intersector_2
Intersector_2
    ATTRS_ACCUM_MODE = Use Attributes From One Feature
    CLEANING_TOLERANCE_LOOKUP = AUTO
    DEAGGREGATE_INPUT = Yes
    GENERATE_LIST_DROP = NO
    IGNORE_HEIGHTS = YES
    INTERSECTION_MODE = GROUP
    MEASURE_TYPE_LOOKUP = CONTINUOUS
    NODE_NUM_ATTR = _node_number
    OV_ATTR = _overlaps
    SEG_ATTR = _segments
    SEPARATE_COLLINEAR_SEGMENTS = No
    CLEANING_TOLERANCE = Automatic
    DUPLICATE_Z_NODES = No
    MEASURE_TYPE = Continuous
    PERFORM_SELF_INTERSECTION = No
    INTERSECTED -> Tester_5
Tester_5
    BOOL_OP = OR
    TEST_CLAUSE = TEST @Value(_segments) = 1
    TEST_MODE = TEST
    PASSED -> CenterPointReplacer_3
CenterPointReplacer_3
    POINTTYPE = CENTER
    POINT -> AttributeKeeper_3
AttributeKeeper_3
    CREATE_BULK_MODE_FEATURES = NO
    KEEP_ATTRS = cota
    -> CELA
    -> Reprojector_2

Bookmark: CAPTURAR_VALOR COTA
Reprojector_2
    DEST = $(EPSG)
    INTERPOLATION_TYPE = ,NearestNeighbor
    RASTER_CELL_SIZE_LOOKUP = ,PreserveCells
    RASTER_TOLERANCE = 0.0
    SOURCE = Read from feature
    INTERPOLATION_TYPE_NAME = Nearest Neighbor
    RASTER_CELL_SIZE = Preserve Cells
    REPROJECTED -> AttributeRenamer
AttributeRenamer
    ATTR_TABLE = RENAME_SET_DEFAULT cota > cota_curva
    -> PointOnRasterValueExtractor [POINT]
GEOTIFF (reader GEOTIFF_1)
    -> Reprojector
Reprojector
    DEST = $(EPSG)
    INTERPOLATION_TYPE = ,NearestNeighbor
    RASTER_CELL_SIZE_LOOKUP = ,PreserveCells
    RASTER_TOLERANCE = 0.0
    SOURCE = Read from feature
    INTERPOLATION_TYPE_NAME = Nearest Neighbor
    RASTER_CELL_SIZE = Preserve Cells
    REPROJECTED -> PointOnRasterValueExtractor [RASTER]
    REPROJECTED -> GEOTIFF
GEOTIFF: Inspector
PointOnRasterValueExtractor
    INTERPOLATION_TYPE = NearestNeighbor
    INTERPOLATION_TYPE_NAME = Nearest Neighbor
    POINT -> AttributeCreator_2
AttributeCreator_2
    ATTR_TABLE:
      SET_TO cota = @round(@Value(_band{0}.value),2)
      SET_TO mi = @Value(fme_basename)
      SET_TO obs
    -> Tester_6
Tester_6
    BOOL_OP = COMPOSITE
    COMPOSITE_TEST = 1 AND 2
    TEST_CLAUSE:
      TEST @Value(cota) > 0
      TEST @Value(cota) < @sum(@Value(cota_curva),$(Equidistancia))
    TEST_MODE = TEST
    PASSED -> Tester_7
Tester_7
    BOOL_OP = OR
    TEST_CLAUSE = TEST @Value(cota) <= @Value(cota_curva)
    TEST_MODE = TEST
    PASSED -> AttributeCreator_3
    FAILED -> AttributeKeeper_4
AttributeCreator_3
    ATTR_TABLE = SET_TO obs = cota curva depressao
    -> AttributeKeeper_4
AttributeKeeper_4
    CREATE_BULK_MODE_FEATURES = NO
    KEEP_ATTRS = cota,mi,obs
    -> pontos_cotados (writer OGCGEOPACKAGE_2)
    -> Pontos
pontos_cotados (writer OGCGEOPACKAGE_2)
    attributes: cota float, mi text(50), obs text(50)
Pontos: Inspector

Bookmark: CRIA PONTO COTADO
CELA: Inspector
