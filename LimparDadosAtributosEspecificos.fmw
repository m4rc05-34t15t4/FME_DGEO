FME workspace LimparDadosAtributosEspecificos.fmw

Parameters:
- DestDataset_POSTGIS = TesteFME   # Connection
- SourceDataset_POSTGIS_2 = 1905_3_SO   # Connection
- FEATURE_TYPES_2 = cb.adm_area_pub_militar_a cb.adm_descontinuidade_geometrica_a cb.adm_descontinuidade_geometrica_p cb.adm_edif_pub_civil_a cb.adm_edif_pub_civil_p cb.adm_edif_pub_militar_a cb.adm_edif_pub_militar_p cb.adm_posto_fiscal_a cb.adm_posto_fiscal_p cb.adm_posto_pol_rod_a cb.adm_posto_pol_rod_p cb.asb_area_abast_agua_a cb.asb_area_saneamento_a cb.asb_cemiterio_a cb.asb_cemiterio_p cb.asb_dep_abast_agua_a cb.asb_dep_abast_agua_p cb.asb_dep_saneamento_a cb.asb_dep_saneamento_p cb.asb_descontinuidade_geometrica_a cb.asb_descontinuidade_geometrica_l cb.asb_descontinuidade_geometrica_p cb.asb_edif_abast_agua_a cb.asb_edif_abast_agua_p cb.asb_edif_saneamento_a cb.asb_edif_saneamento_p cb.aux_descontinuidade_geometrica_a cb.aux_descontinuidade_geometrica_l cb.aux_descontinuidade_geometrica_p cb.eco_area_agrop_ext_veg_pesca_a cb.eco_area_comerc_serv_a cb.eco_area_ext_mineral_a cb.eco_area_industrial_a cb.eco_deposito_geral_a cb.eco_deposito_geral_p cb.eco_descontinuidade_geometrica_a cb.eco_descontinuidade_geometrica_l cb.eco_descontinuidade_geometrica_p cb.eco_edif_agrop_ext_veg_pesca_a cb.eco_edif_agrop_ext_veg_pesca_p cb.eco_edif_comerc_serv_a cb.eco_edif_comerc_serv_p cb.eco_edif_ext_mineral_a cb.eco_edif_ext_mineral_p cb.eco_edif_industrial_a cb.eco_edif_industrial_p cb.eco_equip_agropec_a cb.eco_equip_agropec_l cb.eco_equip_agropec_p cb.eco_ext_mineral_a cb.eco_ext_mineral_p cb.eco_plataforma_a cb.eco_plataforma_p cb.edu_area_ensino_a cb.edu_area_lazer_a cb.edu_area_religiosa_a cb.edu_area_ruinas_a cb.edu_arquibancada_a cb.edu_arquibancada_p cb.edu_campo_quadra_a cb.edu_campo_quadra_p cb.edu_coreto_tribuna_a cb.edu_coreto_tribuna_p cb.edu_descontinuidade_geometrica_a cb.edu_descontinuidade_geometrica_l cb.edu_descontinuidade_geometrica_p cb.edu_edif_const_lazer_a cb.edu_edif_const_lazer_p cb.edu_edif_const_turistica_a cb.edu_edif_const_turistica_p cb.edu_edif_ensino_a cb.edu_edif_ensino_p cb.edu_edif_religiosa_a cb.edu_edif_religiosa_p cb.edu_piscina_a cb.edu_pista_competicao_l cb.edu_ruina_a cb.edu_ruina_p cb.enc_antena_comunic_p cb.enc_area_comunicacao_a cb.enc_area_energia_eletrica_a cb.enc_descontinuidade_geometrica_a cb.enc_descontinuidade_geometrica_p cb.enc_edif_comunic_a cb.enc_edif_comunic_p cb.enc_edif_energia_a cb.enc_edif_energia_p cb.enc_est_gerad_energia_eletr_a cb.enc_est_gerad_energia_eletr_l cb.enc_est_gerad_energia_eletr_p cb.enc_grupo_transformadores_a cb.enc_grupo_transformadores_p cb.enc_hidreletrica_a cb.enc_hidreletrica_l cb.enc_hidreletrica_p cb.enc_ponto_trecho_energia_p cb.enc_termeletrica_a cb.enc_termeletrica_p cb.enc_torre_comunic_p cb.enc_torre_energia_p cb.enc_trecho_comunic_l cb.enc_trecho_energia_l cb.enc_zona_linhas_energia_com_a cb.hid_area_umida_a cb.hid_bacia_hidrografica_a cb.hid_banco_areia_a cb.hid_banco_areia_l cb.hid_barragem_a cb.hid_barragem_l cb.hid_barragem_p cb.hid_comporta_l cb.hid_comporta_p cb.hid_confluencia_p cb.hid_corredeira_a cb.hid_corredeira_l cb.hid_corredeira_p cb.hid_descontinuidade_geometrica_l cb.hid_descontinuidade_geometrica_p cb.hid_fonte_dagua_p cb.hid_foz_maritima_a cb.hid_foz_maritima_l cb.hid_foz_maritima_p cb.hid_ilha_a cb.hid_ilha_l cb.hid_ilha_p cb.hid_limite_massa_dagua_l cb.hid_massa_dagua_a cb.hid_natureza_fundo_a cb.hid_natureza_fundo_l cb.hid_natureza_fundo_p cb.hid_ponto_drenagem_p cb.hid_ponto_inicio_drenagem_p cb.hid_quebramar_molhe_a cb.hid_quebramar_molhe_l cb.hid_queda_dagua_a cb.hid_queda_dagua_l cb.hid_queda_dagua_p cb.hid_recife_a cb.hid_recife_l cb.hid_recife_p cb.hid_reservatorio_hidrico_a cb.hid_rocha_em_agua_a cb.hid_rocha_em_agua_p cb.hid_sumidouro_vertedouro_p cb.hid_terreno_suj_inundacao_a cb.hid_trecho_drenagem_l cb.hid_trecho_massa_dagua_a cb.lim_area_de_litigio_a cb.lim_area_desenv_controle_a cb.lim_area_desenv_controle_p cb.lim_area_especial_a cb.lim_area_especial_p cb.lim_area_particular_a cb.lim_area_politico_adm_a cb.lim_area_uso_comunitario_a cb.lim_area_uso_comunitario_p cb.lim_bairro_a cb.lim_delimitacao_fisica_l cb.lim_descontinuidade_geometrica_a cb.lim_descontinuidade_geometrica_p cb.lim_distrito_a cb.lim_limite_area_especial_l cb.lim_limite_intra_munic_adm_l cb.lim_limite_operacional_l cb.lim_limite_particular_l cb.lim_limite_politico_adm_l cb.lim_linha_de_limite_l cb.lim_marco_de_limite_p cb.lim_municipio_a cb.lim_outras_unid_protegidas_a cb.lim_outras_unid_protegidas_p cb.lim_outros_limites_oficiais_l cb.lim_pais_a cb.lim_regiao_administrativa_a cb.lim_sub_distrito_a cb.lim_terra_indigena_a cb.lim_terra_indigena_p cb.lim_terra_publica_a cb.lim_terra_publica_p cb.lim_unidade_conserv_nao_snuc_a cb.lim_unidade_conserv_nao_snuc_p cb.lim_unidade_federacao_a cb.lim_unidade_protecao_integral_a cb.lim_unidade_protecao_integral_p cb.lim_unidade_uso_sustentavel_a cb.lim_unidade_uso_sustentavel_p cb.loc_aglom_rural_de_ext_urbana_p cb.loc_aglomerado_rural_isolado_p cb.loc_aglomerado_rural_p cb.loc_area_edificada_a cb.loc_area_habitacional_a cb.loc_area_urbana_isolada_a cb.loc_capital_p cb.loc_cidade_p cb.loc_descontinuidade_geometrica_a cb.loc_descontinuidade_geometrica_l cb.loc_descontinuidade_geometrica_p cb.loc_edif_habitacional_a cb.loc_edif_habitacional_p cb.loc_edificacao_a cb.loc_edificacao_p cb.loc_hab_indigena_a cb.loc_hab_indigena_p cb.loc_localidade_p cb.loc_nome_local_p cb.loc_vila_p cb.pto_area_est_med_fenom_a cb.pto_descontinuidade_geometrica_a cb.pto_descontinuidade_geometrica_p cb.pto_edif_constr_est_med_fen_a cb.pto_edif_constr_est_med_fen_p cb.pto_pto_controle_p cb.pto_pto_est_med_fenomenos_p cb.pto_pto_geod_topo_controle_p cb.pto_pto_ref_geod_topo_p cb.rel_alter_fisiog_antropica_a cb.rel_alter_fisiog_antropica_l cb.rel_curva_batimetrica_l cb.rel_curva_nivel_l cb.rel_descontinuidade_geometrica_a cb.rel_descontinuidade_geometrica_l cb.rel_descontinuidade_geometrica_p cb.rel_dolina_a cb.rel_dolina_p cb.rel_duna_a cb.rel_duna_p cb.rel_elemento_fisiog_natural_a cb.rel_elemento_fisiog_natural_l cb.rel_elemento_fisiog_natural_p cb.rel_gruta_caverna_p cb.rel_pico_p cb.rel_ponto_cotado_altimetrico_p cb.rel_ponto_cotado_batimetrico_p cb.rel_rocha_a cb.rel_rocha_p cb.rel_terreno_exposto_a cb.sau_area_saude_a cb.sau_area_servico_social_a cb.sau_descontinuidade_geometrica_a cb.sau_descontinuidade_geometrica_p cb.sau_edif_saude_a cb.sau_edif_saude_p cb.sau_edif_servico_social_a cb.sau_edif_servico_social_p cb.tra_area_duto_a cb.tra_area_estrut_transporte_a cb.tra_arruamento_l cb.tra_atracadouro_a cb.tra_atracadouro_l cb.tra_atracadouro_p cb.tra_caminho_aereo_l cb.tra_ciclovia_l cb.tra_condutor_hidrico_l cb.tra_cremalheira_l cb.tra_cremalheira_p cb.tra_descontinuidade_geometrica_a cb.tra_descontinuidade_geometrica_l cb.tra_descontinuidade_geometrica_p cb.tra_eclusa_a cb.tra_eclusa_l cb.tra_eclusa_p cb.tra_edif_constr_aeroportuaria_a cb.tra_edif_constr_aeroportuaria_p cb.tra_edif_constr_portuaria_a cb.tra_edif_constr_portuaria_p cb.tra_edif_metro_ferroviaria_a cb.tra_edif_metro_ferroviaria_p cb.tra_edif_rodoviaria_a cb.tra_edif_rodoviaria_p cb.tra_entroncamento_p cb.tra_faixa_seguranca_a cb.tra_fundeadouro_a cb.tra_fundeadouro_l cb.tra_fundeadouro_p cb.tra_funicular_l cb.tra_funicular_p cb.tra_galeria_bueiro_l cb.tra_galeria_bueiro_p cb.tra_girador_ferroviario_p cb.tra_identific_trecho_rod_p cb.tra_local_critico_a cb.tra_local_critico_l cb.tra_local_critico_p cb.tra_obstaculo_navegacao_a cb.tra_obstaculo_navegacao_l cb.tra_obstaculo_navegacao_p cb.tra_passag_elevada_viaduto_l cb.tra_passag_elevada_viaduto_p cb.tra_passagem_nivel_p cb.tra_patio_a cb.tra_patio_p cb.tra_pista_ponto_pouso_a cb.tra_pista_ponto_pouso_l cb.tra_pista_ponto_pouso_p cb.tra_ponte_l cb.tra_ponte_p cb.tra_ponto_duto_p cb.tra_ponto_ferroviario_p cb.tra_ponto_hidroviario_p cb.tra_ponto_rodoviario_p cb.tra_posto_combustivel_a cb.tra_posto_combustivel_p cb.tra_sinalizacao_p cb.tra_travessia_l cb.tra_travessia_p cb.tra_travessia_pedestre_l cb.tra_travessia_pedestre_p cb.tra_trecho_duto_l cb.tra_trecho_ferroviario_l cb.tra_trecho_hidroviario_l cb.tra_trecho_rodoviario_l cb.tra_trilha_picada_l cb.tra_tunel_l cb.tra_tunel_p cb.veg_brejo_pantano_a cb.veg_caatinga_a cb.veg_campinarana_a cb.veg_campo_a cb.veg_cerrado_cerradao_a cb.veg_descontinuidade_geometrica_l cb.veg_descontinuidade_geometrica_p cb.veg_estepe_a cb.veg_floresta_a cb.veg_macega_chavascal_a cb.veg_mangue_a cb.veg_veg_area_contato_a cb.veg_veg_cultivada_a cb.veg_veg_restinga_a cb.veg_vegetacao_a public.aux_area_a public.aux_linha_l public.aux_moldura_a public.aux_objeto_desconhecido_a public.aux_objeto_desconhecido_l public.aux_objeto_desconhecido_p public.aux_ponto_p public.raster_columns

Readers:
- POSTGIS_3: POSTGIS from $(SourceDataset_POSTGIS_2)

Writers:
- POSTGIS_2: POSTGIS to $(DestDataset_POSTGIS)

adm_area_pub_civil_a (reader POSTGIS_3)
    attributes: id serial,PrimaryKey, geometriaaproximada int2, id_org_pub_civil uuid, cod_folha varchar(80), mid varchar(80), id_complexo_gerad_energ_eletr uuid, indice int2, situacaocosta int2, tipoelemnat int2, tipotravessiaped int2, id_via_ferrea uuid, nrlinhas int2, areaoficial varchar(15), coincidecomdentrode int2, tiporef int2, alturaestimada float8, tipoqueda int2, multimodal int2, espessuradap float4, potenciafiscalizada float8, id_aldeia_indigena uuid, tipotravessia int2, tipoptoenergia int2, vaolivrehoriz float4, tipoptoestmed int2, tipoterrexp int2, descricao varchar(255), usoprincipal int2, tipoptocontrole int2, tipoobst int2,
      tipodelimfis int2, tipodivisaocnae int2, tipoatracad int2, denominacaoassociada int2, outrarefalt varchar(80), tipobrejopantano int2, materialpredominante int2, anodereferencia int4, atolegal varchar(100), id_org_industrial uuid, tipocampo int2, obssituacao varchar(100), namaximomaximorum int4, altitudeortometrica float8, r_table_name text, navegabilidade int2, eixoprincipal int2, largura float8, id_org_ext_mineral uuid, tipogrutacaverna int2, nivelatencao int2, tipofontedagua int2, tipolocalcrit int2, tipoedifcomercserv int2, opvalidacao varchar(80), opaquisicao varchar(80), identificador varchar(80), id_complexo_abast_agua uuid, orgresp varchar(80), datainicioaquisicao date,
      arranjofases varchar(80), tipoplataforma int2, extensaotrecho float4, id_duto uuid, ocorrenciaem int2, referencialaltim int2, trafego int2, tipocombustivel int2, id_hidrovia uuid, revestimento int2, escala varchar(80), blocksize_x int4, tipoedifrod int2, tipopista int2, regime int2, proximidade int2, tipoptorefgeodtopo int2, tipoedifcomunic int2, codprojeto varchar(80), tipotrechomassa int2, id_org_saude uuid, emarruamento int2, procextracao int2, inom varchar(80), cultivopredominante int2, isolada int2, nrpistas int4, tipoedifmil int2, tipotrechoduto int2, caladomax float4,
      nivelotto int4, construcao int2, tipolimmassa int2, tipotorre int2, regular_blocking bool, id_estrut_apoio uuid, usopista int2, tipoestgerad int2, engrespaquisicao varchar(80), situacaoespacial int2, tipoedifcivil int2, nodata_values text, cota int4, datafimreambulacao date, nomeabrev varchar(50), destenergelet int2, mattransp int2, outrarefplan varchar(80), sigla varchar(6), pesosuportmaximo float4, vaovertical float4, tipocapital int2, tipoedifagropec int2, velocidademedcorrente float4, areaoficialha float4, eletrificada int2, depressao int2, tipolavoura int2, terreno int2, datafimaquisicao date,
      codigohidreletrica varchar(30), tipoextmin int2, sistemageodesico int2, scale_y float8, unidadevolume int2, finalidade int2, id_complexo_comunicacao uuid, id_est_med_fenomenos uuid, datavisita varchar(80), situacaoagua int2, datainicioedicao2 date, engrespreambulacao varchar(80), posicaorelativa int2, tipopassagviad int2, opedicao2 varchar(80), tipoquebramolhe int2, gabhorizsup float4, formaextracao int2, tipoedifaero int2, concessionaria varchar(80), tipotrechoferrov int2, latitude_gms float8, nome varchar(80), mi varchar(80), tipoediflazer int2, residuo int2, nomecarta varchar(80), modalidade int2, tipocemiterio int2, r_table_schema text,
      tipounidprotinteg int2, tipopocomina int2, datainiciovalidacao date, namaximooperacional int4, anocriacao varchar(4), antropizada int2, datainiciorevedicao1 date, out_db text, tipopostofisc int2, oprevisaoaquisicao varchar(80), tipoedifenergia int2, geracao int2, tipomarcolim int2, vaolivrevertical float4, oprevisaoreambulacao varchar(80), tipolimintramun int2, datafimvalidacao date, id_org_agropec_ext_veg_pesca uuid, motivodescontinuidade int2, posicaoreledific int2, tipodepsaneam int2, bitola int2, obs varchar(255), espacamentoindividuos float4, tipousocaminhoaer int2, tipocampoquadra int2, potenciaoutorgada float8, valorvolume float8, datafimrevedicao1 date, coletiva int2,
      ensino int2, tipodepabast int2, datafimedicao1 date, geocodigo varchar(80), nascente int2, salinidade int2, atividade int2, situacaomarco int2, tratamento int2, funcaoedifmetroferrov int2, engresprevisaoaquisicao varchar(80), tipomacchav int2, codestacao varchar(80), altura float4, tipocondutor int2, jurisdicao int2, id_org_religiosa uuid, tipoequipagropec int2, id_complexo_aeroportuario uuid, tipomassadagua int2, tipoentroncamento int2, tipoedifrelig int2, espessalgas int2, tiporecife int2, desnivel float8, latitude varchar(15), datainiciorevaquisicao date, tipoassociado int2, extensao float8, tipomaqtermica int2,
      tipooutunidprot int2, nrfaixas int4, classe varchar(80), tipoprodutoresiduo int2, emduto int2, especie int2, administracao int2, opreambulacao varchar(80), tipoilha int2, tipoponte int2, tipolimpol int2, alturamediaindividuos float4, id_subestacao_ener_eletr uuid, alturalamina float4, modaluso int2, situacaoemagua int2, longitude_gms float8, tipoexposicao int2, situacaofisica int2, tipounidusosust int2, id_complexo_habitacional uuid, rede int2, alturamediamargem float4, nometi varchar(100), longitude varchar(15), compartilhado int2, gabvertsup float4, anoaquisicao varchar(80), grupoetnico varchar(100), tipotrechocomunic int2,
      periodicidadeinunda char(20), profundidademedia float4, ndutos int4, chamine int2, tipoalterantrop int2, setor int2, blocksize_y int4, caracteristicafloresta int2, codigootto int4, operacional int2, scale_x float8, tipoedifabast int2, same_alignment bool, cotacomprovada int2, tipotunel int2, id_org_comerc_serv uuid, id_trecho_curso_dagua uuid, tipoclassecnae int2, codtrechorodov varchar(80), tipoareausocomun int2, matconstr int2, denso int2, codtrechoferrov varchar(80), datafimrevaquisicao date, tipooutlimofic int2, materializado int2, datafimedicao2 date, datasituacaojuridica date, classificacao varchar(80), id_org_ensino uuid,
      homologacao int2, especiepredominante int2, religiao varchar(80), tiporesiduo int2, tipoedifturist int2, combrenovavel int2, spatial_index bool, relacionado int2, tipolimoper int2, classificacaoporte int2, destinacaofundeadouro int2, calado float8, causaexposicao int2, tipoareaumida int2, tiposumvert int2, situacaojuridica int2, pixel_types text, id_via_rodoviaria uuid, tiposecaocnae int2, id_org_servico_social uuid, cargasuportmaxima float4, codponto varchar(80), oprevedicao1 varchar(80), tipopostopol int2, tiposinal int2, tipobanco int2, tipodepgeral int2, reambulado int2, posicaopista int2, id_estrut_transporte uuid,
      historicomodificacao varchar(255), id_org_pub_militar uuid, tipousoedif int2, qualidagua int2, profundidade int4, tipotrechorod int2, larguramedia float4, orgaoenteresp varchar(80), fixa int2, tipoconteudo int2, engrespvalidacaoedicao varchar(80), causa int2, r_table_catalog text, tensaoeletrica float8, situamare int2, dentrodepoligono int2, referencialgrav int2, tipocaminhoaereo int2, datainicioedicao1 date, datainicioreambulacao date, opedicao1 varchar(80), num_bands int4, id_complexo_lazer uuid, codigoestacao varchar(80), numcircuitos int4, codiso3166 varchar(80), canteirodivisorio int2, perimetrooficial float4, r_raster_column text, tiporocha int2,
      tipolimareaesp int2, tipoedifsaneam int2, tipocerr int2, tipoaglomrurisol int2, tipoedifport int2, volumeutil int4, caladomaxseca float4, srid int4, destinadoa int2, ovgd int2, id_complexo_saneamento uuid, id_complexo_portuario uuid
    -> AttributeRemover
    -> _All__2
AttributeRemover
    REMOVE_ATTRS = cod_folha
    -> AttributeCreator
AttributeCreator
    ATTR_TABLE = SET_TO cod_folha
    -> AttributeRemover_Output
    -> Table1 (writer POSTGIS_2)
AttributeRemover_Output: Inspector
Table1 (writer POSTGIS_2)
_All__2: Inspector
_All_: Inspector
