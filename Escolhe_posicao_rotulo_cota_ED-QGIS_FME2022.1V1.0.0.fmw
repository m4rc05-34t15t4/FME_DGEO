FME workspace Escolhe_posicao_rotulo_cota_ED-QGIS_FME2022.1V1.0.0.fmw

Parameters:
- Nome_BD = 1372-3-NO_orto_ed
- EPSG = EPSG:31985
- Escala = 25000
- Camadas_lidas = edgv.aux_insumo_externo_a edgv.aux_insumo_externo_l edgv.aux_insumo_externo_p edgv.aux_moldura_a edgv.aux_moldura_area_continua_a edgv.aux_revisao_a edgv.aux_revisao_l edgv.aux_revisao_p edgv.aux_validacao_a edgv.aux_validacao_l edgv.aux_validacao_p edgv.centroide_area_sem_dados_p edgv.centroide_elemento_hidrografico_p edgv.centroide_ilha_p edgv.centroide_limite_especial_p edgv.centroide_massa_dagua_p edgv.cobter_massa_dagua_a edgv.constr_extracao_mineral_a edgv.constr_extracao_mineral_p edgv.delimitador_area_sem_dados_l edgv.delimitador_elemento_hidrografico_l edgv.delimitador_limite_especial_l edgv.delimitador_massa_dagua_l edgv.edicao_area_pub_militar_l edgv.edicao_area_sem_dados_a edgv.edicao_articulacao_imagem_a edgv.edicao_identificador_trecho_rod_p edgv.edicao_limite_legal_l edgv.edicao_simb_cota_mestra_l edgv.edicao_simb_torre_energia_p edgv.edicao_terra_indigena_l edgv.edicao_texto_generico_l edgv.edicao_texto_generico_p edgv.edicao_unidade_conservacao_l edgv.elemnat_curva_nivel_l edgv.elemnat_elemento_hidrografico_a edgv.elemnat_elemento_hidrografico_l edgv.elemnat_elemento_hidrografico_p edgv.elemnat_ilha_a edgv.elemnat_ilha_p edgv.elemnat_ponto_cotado_p edgv.elemnat_terreno_sujeito_inundacao_a edgv.elemnat_toponimo_fisiografico_natural_l edgv.elemnat_toponimo_fisiografico_natural_p edgv.elemnat_trecho_drenagem_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_ferrovia_l edgv.infra_pista_pouso_a edgv.infra_pista_pouso_l edgv.infra_pista_pouso_p edgv.infra_via_deslocamento_l edgv.llp_aglomerado_rural_p edgv.llp_area_pub_militar_a edgv.llp_localidade_p edgv.llp_nome_local_p edgv.llp_terra_indigena_a edgv.llp_unidade_conservacao_a edgv.llp_unidade_federacao_a
- Escala_1: = 25.000   # Escala 1
- Tam_Nr_Rot_Cota_Perc = 0.035

Readers:
- POSTGIS_1: POSTGIS from $(Nome_BD)

Writers:
- POSTGRES_1: POSTGRES to $(Nome_BD)

aux_insumo_externo_a (reader POSTGIS_1)
    attributes: id uuid, nome varchar(255), fonte varchar(255), observacao varchar(255), operador_criacao varchar(255), data_criacao timestamptz, operador_atualizacao varchar(255), data_atualizacao timestamptz, administracao int2, altitude float4, ancora_horizontal int2, ancora_vertical int2, apresentar_simbologia int2, bitola int2, canteiro_divisorio int2, carta_simbolizacao int2, concessionaria varchar(255), cor varchar(255), cor_buffer varchar(255), corrigido int2, cota int4, cota_comprovada int2, cota_mais_alta int2, data varchar(255), depressao int2, descricao varchar(255), eletrificada int2, em_arruamento int2, espacamento float4, estilo_fonte varchar(255),
      exibir_rotulo_aproximado int2, forma_extracao int2, geometria_aproximada int2, indice int2, inom varchar(255), jurisdicao int2, justificativa varchar(255), justificativa_txt int2, label_x float4, label_y float4, length float4, material_construcao int2, mi varchar(255), nome_abrev_sensor varchar(255), nome_sensor varchar(255), nr_faixas varchar(255), nr_linhas int2, nr_pistas varchar(255), populacao int4, posicao_relativa int2, posicao_rotulo int2, regime int2, revestimento int2, rotular_carta_mini int2, sigla varchar(255), simb_rot float4, simbolizar_carta_mini int2, situacao_em_poligono int2, situacao_fisica int2, sobreposto int2,
      sobreposto_transportes int2, subfase_id int4, tamanho_buffer float4, tamanho_txt float4, texto_edicao varchar(255), tipo int2, tipoproduto int2, trafego int2, uso_pista int2, visivel int2
    -> Reprojector
    -> Features
Note: EDGV 3.0 Orto impl. 2.2.3
Features: Inspector
Reprojector
    DEST = $(EPSG)
    INTERPOLATION_TYPE_NAME = Nearest Neighbor
    RASTER_CELL_SIZE = Preserve Cells
    RASTER_TOLERANCE = 0.0
    REPROJECTED -> AttributeFilter
    REPROJECTED -> Junction_3
AttributeFilter
    ATTR_NAME = fme_feature_type
    ATTR_VALUES = <Empty>,<Missing>,<Null>,<Unfiltered>,edgv.elemnat_ponto_cotado_p,edgv.aux_moldura_a
    edgv.aux_moldura_a -> BoundsExtractor
    edgv.elemnat_ponto_cotado_p -> CoordinateExtractor
    edgv.elemnat_ponto_cotado_p -> FeatureMerger [REQUESTOR]
AttributeFilter_2
    ATTR_NAME = _cx_rot_direcao
    ATTR_VALUES = <Empty>,<Missing>,<Null>,<Unfiltered>,N,NE,E,SE,S,SO,O,NO
    N -> Calc_Score_Element_Box_8 [Box]
    NE -> Calc_Score_Element_Box_7 [Box]
    E -> Calc_Score_Element_Box_6 [Box]
    SE -> Calc_Score_Element_Box_5 [Box]
    S -> Calc_Score_Element_Box_4 [Box]
    SO -> Calc_Score_Element_Box_3 [Box]
    O -> Calc_Score_Element_Box_2 [Box]
    NO -> Calc_Score_Element_Box [Box]
Junction_3
    -> Junction_2
Junction_2
    -> Calc_Score_Element_Box [Elementos]
    -> Calc_Score_Element_Box_2 [Elementos]
    -> Calc_Score_Element_Box_3 [Elementos]
    -> Calc_Score_Element_Box_4 [Elementos]
    -> Calc_Score_Element_Box_5 [Elementos]
    -> Calc_Score_Element_Box_6 [Elementos]
    -> Calc_Score_Element_Box_7 [Elementos]
    -> Calc_Score_Element_Box_8 [Elementos]
Junction_5
    -> Sorter
    -> Reprojector_3
elemnat_ponto_cotado_p: Inspector
AttributeKeeper_2
    CREATE_BULK_MODE_FEATURES = NO
    KEEP_ATTRS = ancora_horizontal,ancora_vertical,id,label_x,label_y,fme_feature_type
    -> aux_insumo_externo_a (writer POSTGRES_1)
aux_insumo_externo_a (writer POSTGRES_1)
    attributes: id uuid, nome varchar(255), fonte varchar(255), observacao varchar(255), operador_criacao varchar(255), data_criacao timestamptz, operador_atualizacao varchar(255), data_atualizacao timestamptz, administracao int2, altitude float4, ancora_horizontal int2, ancora_vertical int2, apresentar_simbologia int2, bitola int2, canteiro_divisorio int2, carta_simbolizacao int2, concessionaria varchar(255), cor varchar(255), cor_buffer varchar(255), corrigido int2, cota int4, cota_comprovada int2, cota_mais_alta int2, data varchar(255), depressao int2, descricao varchar(255), eletrificada int2, em_arruamento int2, espacamento float4, estilo_fonte varchar(255),
      exibir_rotulo_aproximado int2, forma_extracao int2, geometria_aproximada int2, indice int2, inom varchar(255), jurisdicao int2, justificativa varchar(255), justificativa_txt int2, label_x float4, label_y float4, length float4, material_construcao int2, mi varchar(255), nome_abrev_sensor varchar(255), nome_sensor varchar(255), nr_faixas varchar(255), nr_linhas int2, nr_pistas varchar(255), populacao int4, posicao_relativa int2, posicao_rotulo int2, regime int2, revestimento int2, rotular_carta_mini int2, sigla varchar(255), simb_rot float4, simbolizar_carta_mini int2, situacao_em_poligono int2, situacao_fisica int2, sobreposto int2,
      sobreposto_transportes int2, subfase_id int4, tamanho_buffer float4, tamanho_txt float4, texto_edicao varchar(255), tipo int2, tipoproduto int2, trafego int2, uso_pista int2, visivel int2
VertexCreator_5
    MEASURE_TYPE = Continuous
    MODE_NAME = Replace with Point
    XVAL = @Value(label_x)
    YVAL = @Value(label_y)
    ZVAL = @Value(cota)
    -> AttributeCreator_2
AttributeCreator_2
    ATTR_TABLE = SET_TO fme_feature_type = ancora_box_rotulo_cota
    -> Features_2
Junction_6
    -> Reprojector_3
Reprojector_3
    DEST = EPSG:4674
    INTERPOLATION_TYPE_NAME = Nearest Neighbor
    RASTER_CELL_SIZE = Preserve Cells
    RASTER_TOLERANCE = 0.0
    REPROJECTED -> Features_2
Features_2: Inspector
    TACKATTRS = fme_feature_type

Bookmark: Cria Rótulo Cota Padrão
CoordinateExtractor
    IND = 0
    MODE = Specify Coordinate
    X_ATTR = _x
    Y_ATTR = _y
    -> AttributeCreator
AttributeCreator
    ATTR_TABLE:
      SET_TO _qtd_digitos_cota = @FindString(@sum(@double(@Value(cota)),0.000001),.,0)
      SET_TO _xNr = @Evaluate($(Escala) / 100 * 4 * $(Tam_Nr_Rot_Cota_Perc))
      SET_TO _yNr = @Evaluate(@Value(_xNr) * 2)
      SET_TO _xRotulo = @Evaluate(@Value(_xNr) * @Value(_qtd_digitos_cota))
      SET_TO fme_feature_type = caixa_rotulo_cota
    -> Junction
Junction
    -> VertexCreator_3
    -> VertexCreator
    -> VertexCreator_4
    -> VertexCreator_2
VertexCreator
    MEASURE_TYPE = Continuous
    MODE_NAME = Replace with Point
    XVAL = @Value(_x) + @Value(_xRotulo)
    YVAL = @Value(_y)
    ZVAL = @Value(id)
    -> Aggregator
VertexCreator_2
    MEASURE_TYPE = Continuous
    MODE_NAME = Replace with Point
    XVAL = @Value(_x) + @Value(_xRotulo)
    YVAL = @Value(_y) + @Value(_yNr)
    -> Aggregator
VertexCreator_3
    MEASURE_TYPE = Continuous
    MODE_NAME = Replace with Point
    XVAL = @Value(_x)
    YVAL = @Value(_y) + @Value(_yNr)
    -> Aggregator
VertexCreator_4
    MEASURE_TYPE = Continuous
    MODE_NAME = Replace with Point
    XVAL = @Value(_x)
    YVAL = @Value(_y)
    -> Aggregator
Aggregator
    ACCUM_ATTRS_NAME = Use Attributes From One Feature
    AGGREGATE_TYPE = Homogeneous Collection (If Possible)
    GROUP_BY = id
    MODE = Geometry - Assemble One Level
    SEP = ,
    AGGREGATE -> BoundingBoxAccumulator
BoundingBoxAccumulator
    ACCUM_ATTRS_NAME = Use Attributes From One Feature
    GROUP_BY = id
    BOUNDING_BOX -> AttributeKeeper
AttributeKeeper
    CREATE_BULK_MODE_FEATURES = NO
    KEEP_ATTRS = _qtd_digitos_cota,_x,_xNr,_xRotulo,_y,_yNr,cota,cota_comprovada,cota_mais_alta,fme_feature_type,id
    -> quadrado_rotulo_cota
    -> Offsetter
    -> Offsetter_2
    -> Offsetter_3
quadrado_rotulo_cota: Inspector [off]

Bookmark: Caixa_Rotulos_Cota
Offsetter
    MODE = Cartesian Coordinate
    XOFF = @Value(_xNr) / 2
    YOFF = @Value(_xNr) / 2
    ZOFF = 0
    OFFSET -> Offsetter_4
    OFFSET -> AttributeCreator_12
AttributeCreator_12
    ATTR_TABLE = SET_TO _cx_rot_direcao = NE
    -> Rotulo_Cota_NE
    -> Junction_4
Rotulo_Cota_NE: Inspector [off]
Offsetter_4
    MODE = Cartesian Coordinate
    XOFF = (@Value(_xRotulo) + @Value(_xNr) ) * -1
    YOFF = 0
    ZOFF = 0
    OFFSET -> Offsetter_7
    OFFSET -> AttributeCreator_14
AttributeCreator_14
    ATTR_TABLE = SET_TO _cx_rot_direcao = NO
    -> Rotulo_Cota_NO
    -> Junction_4
Rotulo_Cota_NO: Inspector [off]
Offsetter_7
    MODE = Cartesian Coordinate
    XOFF = @Value(_xRotulo) / 2 + @Value(_xNr)  / 2
    YOFF = 0
    ZOFF = 0
    OFFSET -> AttributeCreator_15
AttributeCreator_15
    ATTR_TABLE = SET_TO _cx_rot_direcao = N
    -> Rotulo_Cota_N
    -> Junction_4
Rotulo_Cota_N: Inspector [off]
Offsetter_2
    MODE = Cartesian Coordinate
    XOFF = @Value(_xNr) / 2
    YOFF = @Value(_yNr) / 2 * -1
    ZOFF = 0
    OFFSET -> Offsetter_5
    OFFSET -> AttributeCreator_11
AttributeCreator_11
    ATTR_TABLE = SET_TO _cx_rot_direcao = E
    -> Rotulo_Cota_E
    -> Junction_4
Rotulo_Cota_E: Inspector [off]
Offsetter_5
    MODE = Cartesian Coordinate
    XOFF = (@Value(_xRotulo) + @Value(_xNr)) * -1
    YOFF = 0
    ZOFF = 0
    OFFSET -> AttributeCreator_13
AttributeCreator_13
    ATTR_TABLE = SET_TO _cx_rot_direcao = O
    -> Rotulo_Cota_O
    -> Junction_4
Rotulo_Cota_O: Inspector [off]
Offsetter_3
    MODE = Cartesian Coordinate
    XOFF = @Value(_xNr) / 2
    YOFF = (@Value(_yNr) + (@Value(_xNr) / 2)) * -1
    ZOFF = 0
    OFFSET -> AttributeCreator_7
    OFFSET -> Offsetter_6
AttributeCreator_7
    ATTR_TABLE = SET_TO _cx_rot_direcao = SE
    -> Rotulo_Cota_SE
    -> Junction_4
Rotulo_Cota_SE: Inspector [off]
Offsetter_6
    MODE = Cartesian Coordinate
    XOFF = (@Value(_xRotulo) + @Value(_xNr)) * -1
    YOFF = 0
    ZOFF = 0
    OFFSET -> AttributeCreator_8
    OFFSET -> Offsetter_8
AttributeCreator_8
    ATTR_TABLE = SET_TO _cx_rot_direcao = SO
    -> Rotulo_Cota_SO
    -> Junction_4
Rotulo_Cota_SO: Inspector [off]
Offsetter_8
    MODE = Cartesian Coordinate
    XOFF = @Value(_xRotulo) / 2 + @Value(_xNr)  / 2
    YOFF = 0
    ZOFF = 0
    OFFSET -> AttributeCreator_10
AttributeCreator_10
    ATTR_TABLE = SET_TO _cx_rot_direcao = S
    -> Junction_4
    -> Rotulo_Cota_S
Junction_4
    -> Junction_2
    -> AttributeFilter_2
    -> Junction_6
Rotulo_Cota_S: Inspector [off]

Bookmark: GRID
BoundsExtractor
    XMAX = _xmax
    XMIN = _xmin
    YMAX = _ymax
    YMIN = _ymin
    ZMAX = _zmax
    ZMIN = _zmin
    -> AttributeCreator_9
AttributeCreator_9
    ATTR_LIST = _XMinGrid,@Evaluate(@floor(@Value(_xmin) / ($(Escala) / 100 * 4),0) * ($(Escala) / 100 * 4)),_YMaxGrid,@Evaluate((@floor(@Value(_ymax) / ($(Escala) / 100 * 4),0) + 1 ) * ($(Escala) / 100 * 4))
    -> 2DGridAccumulator_2
2DGridAccumulator_2
    COL_ATTR = _column
    GRID_TYPE = Polygons
    ROW_ATTR = _row
    SIZE_TYPE = Cell Size
    STARTINGCORNER = Upper Left
    XINC = $(Escala) / 100 * 4
    XSEED = @Value(_XMinGrid)
    YINC = $(Escala) / 100 * 4
    YSEED = @Value(_YMaxGrid)
    GRID -> AttributeCreator_3
AttributeCreator_3
    ATTR_TABLE = SET_TO fme_feature_type = grid
    -> Junction_3
    -> Junction_6
    -> 2DGridAccumulator_Grid
2DGridAccumulator_Grid: Inspector [off]

Bookmark: New Bookmark
Calc_Score_Element_Box_8
    FME_FEATURE_TYPE = @Value(fme_feature_type)
    ID = @Value(id)
    _CX_ROT_DIRECAO = @Value(_cx_rot_direcao)
    Elementos_Box -> Junction_5
Calc_Score_Element_Box_7
    FME_FEATURE_TYPE = @Value(fme_feature_type)
    ID = @Value(id)
    _CX_ROT_DIRECAO = @Value(_cx_rot_direcao)
    Elementos_Box -> Junction_5
Calc_Score_Element_Box_6
    FME_FEATURE_TYPE = @Value(fme_feature_type)
    ID = @Value(id)
    _CX_ROT_DIRECAO = @Value(_cx_rot_direcao)
    Elementos_Box -> Junction_5
Calc_Score_Element_Box_5
    FME_FEATURE_TYPE = @Value(fme_feature_type)
    ID = @Value(id)
    _CX_ROT_DIRECAO = @Value(_cx_rot_direcao)
    Elementos_Box -> Junction_5
Calc_Score_Element_Box_4
    FME_FEATURE_TYPE = @Value(fme_feature_type)
    ID = @Value(id)
    _CX_ROT_DIRECAO = @Value(_cx_rot_direcao)
    Elementos_Box -> Junction_5
Calc_Score_Element_Box_3
    FME_FEATURE_TYPE = @Value(fme_feature_type)
    ID = @Value(id)
    _CX_ROT_DIRECAO = @Value(_cx_rot_direcao)
    Elementos_Box -> Junction_5
Calc_Score_Element_Box_2
    FME_FEATURE_TYPE = @Value(fme_feature_type)
    ID = @Value(id)
    _CX_ROT_DIRECAO = @Value(_cx_rot_direcao)
    Elementos_Box -> Junction_5
Calc_Score_Element_Box
    FME_FEATURE_TYPE = @Value(fme_feature_type)
    ID = @Value(id)
    _CX_ROT_DIRECAO = @Value(_cx_rot_direcao)
    Elementos_Box -> Junction_5

Bookmark: Filtrar Box mais limpo
Sorter
    GROUP_BY = rot_cx_id
    SORT_PARM = _score NUMERIC ASCENDING
    SORTED -> Counter
Counter
    CNT_ATTR = _count
    GROUP_BY = rot_cx_id
    SCOPE = Local
    START = 0
    -> Tester_3
    -> Reprojector_3
Tester_3
    BOOL_OP = OR
    TEST_CLAUSE = TEST @Value(_count) = 0
    TEST_MODE = TEST
    PASSED -> AttributeManager
AttributeManager
    ATTR_TABLE:
      RENAME_SET_VALUE rot_cx__cx_rot_direcao > _cx_rot_direcao
      REMOVE _comprimento
      REMOVE _aggr_count
      REMOVE _count
    -> FeatureMerger [SUPPLIER]
FeatureMerger
    ATTR_ACCUM_MODE = Merge Supplier
    ATTR_CONFLICT_RES = Use Requestor
    IGNORE_NULLS = No
    JOIN_KEYS = @Value(id) @Value(rot_cx_id) AUTO
    MERGE_TYPE = Attributes Only
    PROCESS_DUPS = NO
    REJECT_NULL_MISSING_KEYS = No
    SUPPLIERS_FIRST = No
    MERGED -> Reprojector_2
    UNMERGED_REQUESTOR -> Reprojector_2

Bookmark: Defines valores das variaveis
Reprojector_2
    DEST = EPSG:4674
    INTERPOLATION_TYPE_NAME = Nearest Neighbor
    RASTER_CELL_SIZE = Preserve Cells
    RASTER_TOLERANCE = 0.0
    REPROJECTED -> CoordinateExtractor_2
CoordinateExtractor_2
    IND = 0
    MODE = Specify Coordinate
    X_ATTR = _x
    Y_ATTR = _y
    -> AttributeKeeper_4
AttributeKeeper_4
    CREATE_BULK_MODE_FEATURES = NO
    KEEP_ATTRS = _cx_rot_direcao,_score,_x,_y,ancora_horizontal,ancora_vertical,cota,cota_comprovada,cota_mais_alta,data_atualizacao,data_criacao,id,label_x,label_y,observacao,operador_atualizacao,operador_criacao,rot_cx_id,visivel,fme_feature_type
    -> AttributeCreator_6
AttributeCreator_6
    ATTR_TABLE:
      SET_TO label_x = FME_CONDITIONAL:DEFAULT_VALUE'@Value(_x)'BOOL_OP;OR;COMPOSITE_TEST;1;TEST @Value(_cx_rot_direcao) = N'@Value(_x)'BOOL_OP;OR;COMPOSITE_TEST;1;TEST @Value(_cx_rot_direcao) = NE'@Evaluate(@Value(_x) + 0.0001)'BOOL_OP;OR;COMPOSITE_TEST;1;TEST @Value(_cx_rot_direcao) = E'@Evaluate(@Value(_x) + 0.0001)'BOOL_OP;OR;COMPOSITE_TEST;1;TEST @Value(_cx_rot_direcao) = SE'@Evaluate(@Value(_x) + 0.0001)'BOOL_OP;OR;COMPOSITE_TEST;1;TEST @Value(_cx_rot_direcao) = S'@Value(_x)'BOOL_OP;OR;COMPOSITE_TEST;1;TEST @Value(_cx_rot_direcao) = SO'@Evaluate(@Value(_x) - 0.0001)'BOOL_OP;OR;COMPOSITE_TEST;1;TEST @Value(_cx_rot_direcao) = O'@Evaluate(@Value(_x) - 0.0001)'BOOL_OP;OR;COMPOSITE_TEST;1;TEST @Value(_cx_rot_direcao) = NO'@Evaluate(@Value(_x) - 0.0001)'FME_NUM_CONDITIONS9___
      SET_TO label_y = FME_CONDITIONAL:DEFAULT_VALUE'@Evaluate(@Value(_y) + 0.0001)'BOOL_OP;OR;COMPOSITE_TEST;1;TEST @Value(_cx_rot_direcao) = N'@Evaluate(@Value(_y) + 0.0001)'BOOL_OP;OR;COMPOSITE_TEST;1;TEST @Value(_cx_rot_direcao) = NE'@Evaluate(@Value(_y) + 0.0001)'BOOL_OP;OR;COMPOSITE_TEST;1;TEST @Value(_cx_rot_direcao) = E'@Value(_y)'BOOL_OP;OR;COMPOSITE_TEST;1;TEST @Value(_cx_rot_direcao) = SE'@Evaluate(@Value(_y) - 0.0001)'BOOL_OP;OR;COMPOSITE_TEST;1;TEST @Value(_cx_rot_direcao) = S'@Evaluate(@Value(_y) - 0.0001)'BOOL_OP;OR;COMPOSITE_TEST;1;TEST @Value(_cx_rot_direcao) = SO'@Evaluate(@Value(_y) - 0.0001)'BOOL_OP;OR;COMPOSITE_TEST;1;TEST @Value(_cx_rot_direcao) = O'@Value(_y)'BOOL_OP;OR;COMPOSITE_TEST;1;TEST @Value(_cx_rot_direcao) = NO'@Evaluate(@Value(_y) + 0.0001)'FME_NUM_CONDITIONS9___
      SET_TO ancora_horizontal = FME_CONDITIONAL:DEFAULT_VALUE'2'BOOL_OP;OR;COMPOSITE_TEST;1;TEST @Value(_cx_rot_direcao) = N'2'BOOL_OP;OR;COMPOSITE_TEST;1;TEST @Value(_cx_rot_direcao) = NE'1'BOOL_OP;OR;COMPOSITE_TEST;1;TEST @Value(_cx_rot_direcao) = E'1'BOOL_OP;OR;COMPOSITE_TEST;1;TEST @Value(_cx_rot_direcao) = SE'1'BOOL_OP;OR;COMPOSITE_TEST;1;TEST @Value(_cx_rot_direcao) = S'2'BOOL_OP;OR;COMPOSITE_TEST;1;TEST @Value(_cx_rot_direcao) = SO'3'BOOL_OP;OR;COMPOSITE_TEST;1;TEST @Value(_cx_rot_direcao) = O'3'BOOL_OP;OR;COMPOSITE_TEST;1;TEST @Value(_cx_rot_direcao) = NO'3'FME_NUM_CONDITIONS9___
      SET_TO ancora_vertical = FME_CONDITIONAL:DEFAULT_VALUE'1'BOOL_OP;OR;COMPOSITE_TEST;1;TEST @Value(_cx_rot_direcao) = N'1'BOOL_OP;OR;COMPOSITE_TEST;1;TEST @Value(_cx_rot_direcao) = NE'1'BOOL_OP;OR;COMPOSITE_TEST;1;TEST @Value(_cx_rot_direcao) = E'2'BOOL_OP;OR;COMPOSITE_TEST;1;TEST @Value(_cx_rot_direcao) = SE'3'BOOL_OP;OR;COMPOSITE_TEST;1;TEST @Value(_cx_rot_direcao) = S'3'BOOL_OP;OR;COMPOSITE_TEST;1;TEST @Value(_cx_rot_direcao) = SO'3'BOOL_OP;OR;COMPOSITE_TEST;1;TEST @Value(_cx_rot_direcao) = O'2'BOOL_OP;OR;COMPOSITE_TEST;1;TEST @Value(_cx_rot_direcao) = NO'1'FME_NUM_CONDITIONS9___
    -> elemnat_ponto_cotado_p
    -> VertexCreator_5
    -> AttributeKeeper_2

FME custom transformer Calc_Score_Element_Box

Parameters:
- ID = @Value(id)   # id
- FME_FEATURE_TYPE = @Value(fme_feature_type)   # Fme Feature Type
- _CX_ROT_DIRECAO = @Value(_cx_rot_direcao)   # Cx Rot Direcao

Box (input)
    -> AttributeKeeper_3
Elementos (input)
    -> AttributeCreator_2
Elementos_Box (output)

Bookmark: Agrega e separada elementos por box e calcula o score
AttributeKeeper_3
    CREATE_BULK_MODE_FEATURES = NO
    KEEP_ATTRS = id,_cx_rot_direcao
    -> LineOnAreaOverlayer [AREA]
    -> Intersector
    -> PointOnAreaOverlayer [AREA]
AttributeCreator_2
    ATTR_TABLE:
      SET_TO _feature_type_caixa_rotulo = @Value(fme_feature_type)
      SET_TO _id_element = @Value(id)
    -> AttributeKeeper_2
AttributeKeeper_2
    CREATE_BULK_MODE_FEATURES = NO
    KEEP_ATTRS = _feature_type_caixa_rotulo,_id_element
    -> GeometryFilter
GeometryFilter
    FILTER_MODE = SIMPLE
    FILTER_MULTI = FILTER_TYPES]Point]FME_CONTROLLER_QUERY_FILE]]FME_CONTROLLER_CHOICE]Simple
    Point -> PointOnAreaOverlayer [POINT]
    <UNFILTERED> -> Intersector
PointOnAreaOverlayer
    ATTR_ACCUM_MODE = Prefic Incoming
    DEAGGREGATE_INPUT = Yes
    INCOMING_PREFIX = rot_cx_
    OV_ATTR = _overlaps
    POLYS_FIRST = NO
    POINT -> Tester_2
Intersector
    ATTRS_ACCUM_MODE = Merge Attributes
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> LineOnAreaOverlayer [LINE]
LineOnAreaOverlayer
    ATTR_ACCUM_MODE = Prefix Incoming
    CLEANING_TOLERANCE = Automatic
    DEAGGREGATE_INPUT = Yes
    INCOMING_PREFIX = rot_cx_
    OV_ATTR = _overlaps
    LINE -> Tester
Tester
    BOOL_OP = COMPOSITE
    COMPOSITE_TEST = 1 AND 2
    TEST_CLAUSE:
      TEST @Value(_id_element) != @Value(rot_cx_id)
      TEST rot_cx__cx_rot_direcao ATTRIBUTE_HAS_A_VALUE ""
    TEST_MODE = TEST
    PASSED -> AttributeCreator_4
AttributeCreator_4
    ATTR_TABLE = SET_TO _comprimento = @Length()
    -> Tester_2
Tester_2
    BOOL_OP = OR
    TEST_CLAUSE = TEST @Value(_overlaps) > 0
    TEST_MODE = TEST
    PASSED -> AttributeCreator_5
Note: Calcula o Score com base no Peso da feature
AttributeCreator_5
    ATTR_TABLE = SET_TO _score = FME_CONDITIONAL:DEFAULT_VALUE'_FME_NO_OP_'BOOL_OP;OR;COMPOSITE_TEST;1;TEST @Value(_feature_type_caixa_rotulo) = edgv.elemnat_ponto_cotado_p'@Evaluate(500)'BOOL_OP;OR;COMPOSITE_TEST;1;TEST @Value(_feature_type_caixa_rotulo) = edgv.edicao_identificador_trecho_rod_p'@Evaluate(750)'BOOL_OP;OR;COMPOSITE_TEST;1;TEST @Value(_feature_type_caixa_rotulo) = edgv.edgv.elemnat_curva_nivel_l'@Evaluate(1 * @Value(_comprimento))'BOOL_OP;OR;COMPOSITE_TEST;1;TEST @Value(_feature_type_caixa_rotulo) = caixa_rotulo_cota'@Evaluate(3 * @Value(_comprimento))'BOOL_OP;OR;COMPOSITE_TEST;1;TEST @Value(_feature_type_caixa_rotulo) = edgv.elemnat_trecho_drenagem_l'@Evaluate(5 * @Value(_comprimento))'BOOL_OP;OR;COMPOSITE_TEST;1;TEST @Value(_feature_type_caixa_rotulo) = edgv.edicao_texto_generico_l'@Evaluate(7 * @Value(_comprimento))'BOOL_OP;OR;COMPOSITE_TEST;1;TEST @Value(_feature_type_caixa_rotulo) = edgv.infra_via_deslocamento_l'@Evaluate(10 * @Value(_comprimento))'BOOL_OP;OR;COMPOSITE_TEST;1;TEST @Value(_feature_type_caixa_rotulo) = edgv.infra_ferrovia_l'@Evaluate(10 * @Value(_comprimento))'BOOL_OP;OR;COMPOSITE_TEST;1;TEST @Value(_feature_type_caixa_rotulo) = grid'@Evaluate(30 * @Value(_comprimento))'BOOL_OP;OR;COMPOSITE_TEST;1;TEST @Value(_feature_type_caixa_rotulo) = edgv.aux_moldura_a'@Evaluate(50 * @Value(_comprimento))'BOOL_OP;OR;COMPOSITE_TEST;1;TEST @Right(@Value(_feature_type_caixa_rotulo),2) = _p'@Evaluate(400)'BOOL_OP;OR;COMPOSITE_TEST;1 OR 2;TEST @Right(@Value(_feature_type_caixa_rotulo),2) = _l;TEST @Right(@Value(_feature_type_caixa_rotulo),2) = _a'@Evaluate(5 * @Value(_comprimento))'FME_NUM_CONDITIONS13___
    -> Aggregator_2
Aggregator_2
    ACCUM_ATTRS_NAME = Drop Incoming Attributes
    AGGREGATE_TYPE = Homogeneous Collection (If Possible)
    COUNT_ATTR = _aggr_count
    GROUP_BY = rot_cx_id rot_cx__cx_rot_direcao
    MODE = Geometry - Assemble One Level
    SEP = ,
    SUM = _comprimento _score
    AGGREGATE -> AttributeCreator
AttributeCreator
    ATTR_TABLE = SET_TO fme_feature_type = elementos_agreg_box
    -> Elementos_Box (output)
