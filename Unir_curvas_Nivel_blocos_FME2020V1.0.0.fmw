FME workspace Unir_curvas_Nivel_blocos_FME2020V1.0.0.fmw

Parameters:
- SourceDataset_SHAPEFILE = $(FME_MF_DIR)Outros\Teste_curvas_blocoB\nearest_neighbour.shp   # Source Esri Shapefile(s)
- SourceDataset_SHAPEFILE_3 = $(FME_MF_DIR)Outros\Teste_curvas_blocoB\moldura_teste.shp   # Source Esri Shapefile(s)
- DestDataset_OGCGEOPACKAGE = $(FME_MF_DIR)Outros\Teste_curvas_blocoB\curvas_blocos.gpkg   # GeoPackage File
- DestDataset_OGCGEOPACKAGE_3 = $(FME_MF_DIR)Outros\Teste_curvas_blocoB\curvas_blocos_partidas.gpkg   # GeoPackage File

Readers:
- SHAPEFILE_1: SHAPEFILE from $(SourceDataset_SHAPEFILE)
- SHAPEFILE_2: SHAPEFILE from $(SourceDataset_SHAPEFILE_3)

Writers:
- OGCGEOPACKAGE_1: OGCGEOPACKAGE to $(DestDataset_OGCGEOPACKAGE)
- OGCGEOPACKAGE_2: OGCGEOPACKAGE to $(DestDataset_OGCGEOPACKAGE_3)

nearest_neighbour (reader SHAPEFILE_1)
    attributes: ID number(16,0), Z double
    -> nearest_neighbour
    -> Clipper [CLIPPEE]
nearest_neighbour: Inspector
moldura_teste (reader SHAPEFILE_2)
    attributes: id long
    -> Bufferer
    -> moldura_teste
    -> Dissolver
moldura_teste: Inspector
Bufferer
    ANGLE = 22.5
    CAP_STYLE = Arc
    CORNER_STYLE = Arc
    MODE = AREA
    OFFSET = 6.5
    OFFSET_UNITS = NONE
    PRECISION = APPROX
    BUFFERED -> Clipper [CLIPPER]
    BUFFERED -> Intersector
    BUFFERED -> Bufferer_Buffered
    BUFFERED -> GeometryCoercer
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> Clipper_Outside
    OUTSIDE -> Deaggregator
Clipper_Outside: Inspector
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> UUIDGenerator
UUIDGenerator
    UUID_ATTR = _uuid
    -> Junction
    -> Intersector
    -> UUIDGenerator_Output
    -> PointOnLineOverlayer [LINE]
    -> CoordinateExtractor
CoordinateExtractor [off]
    IND = 0
    MODE = Specify Coordinate
    X_ATTR = _x
    Y_ATTR = _y
    Z_ATTR = _z
    -> PointOnLineOverlayer_4 [LINE]
UUIDGenerator_Output: Inspector
Intersector
    ATTRS_ACCUM_MODE = Use Attributes From One Feature
    CLEANING_TOLERANCE = Automatic
    DEAGGREGATE_INPUT = Yes
    DIRECTION_NAME = direction
    DUPLICATE_Z_NODES = No
    GENERATE_LIST_DROP = NO
    MEASURE_TYPE = Continuous
    NODE_NUM_ATTR = _node_number
    OV_ATTR = _overlaps
    PERFORM_SELF_INTERSECTION = No
    SEG_ATTR = _segments
    SEPARATE_COLLINEAR_SEGMENTS = No
    NODE -> PointOnLineOverlayer [POINT]
PointOnLineOverlayer
    ATTR_ACCUM_MODE = Prefix Incoming
    DEAGGREGATE_INPUT = Yes
    INCOMING_PREFIX = CURVAS_
    MEASURE_TYPE = Continuous
    MERGE_MEASURES = Yes
    OV_ATTR = _overlaps_curvas
    TOLERANCE = 1
    POINT -> PointOnLineOverlayer_2 [POINT]
Junction [off]
    -> AttributeKeeper_3
    -> Aggregator
Bufferer_Buffered: Inspector
GeometryCoercer
    GQUERY:
      for $geom in //geometry
      where $geom/count(parent::geometry) = 0
      return number($geom/@fme_id)
    KIND = fme_line
    COERCED -> PointOnLineOverlayer_2 [LINE]
PointOnLineOverlayer_2
    DEAGGREGATE_INPUT = Yes
    MEASURE_TYPE = Continuous
    MERGE_MEASURES = Yes
    OV_ATTR = _overlaps_buffer
    TOLERANCE = 1
    POINT -> Tester
Tester
    BOOL_OP = COMPOSITE
    COMPOSITE_TEST = 1 AND 2
    TEST_CLAUSE:
      TEST @Value(_overlaps_buffer) > 0
      TEST @Value(_overlaps_curvas) > 0
    TEST_MODE = TEST
    PASSED -> Intersector_Node
    PASSED -> AttributeCreator
    FAILED -> Tester_Failed
AttributeCreator
    ATTR_TABLE:
      SET_TO Z = @Value(CURVAS_Z)
      SET_TO ID = @Value(CURVAS_ID)
      SET_TO UUID = @Value(CURVAS__uuid)
    -> AttributeKeeper
AttributeKeeper
    KEEP_ATTRS = ID,Z,UUID
    -> NeighborFinder [CANDIDATE]
    -> PointOnLineOverlayer_3 [POINT]
NeighborFinder
    CANDIDATES_FIRST = No
    GROUP_BY = Z
    INSERT_VERTEX = Yes
    K = 1
    MEASURES_FROM_CANDIDATE = Yes
    MEASURE_TYPE = Continuous
    MODE = Candidates Only
    TREAT_POLYGON_AS = Lines
    MATCHED -> NeighborFinder_MatchedBase
    MATCHED -> VertexCreator
    MATCHED -> PointOnLineOverlayer_4 [POINT]
    UNMATCHED_BASE -> NeighborFinder_UnmatchedBase
    UNMATCHED_CANDIDATE -> NeighborFinder_UnmatchedCandidate
PointOnLineOverlayer_4
    ATTR_ACCUM_MODE = Merge Incoming
    ATTR_CONFLICT_RES = Use Original
    DEAGGREGATE_INPUT = Yes
    MEASURE_TYPE = Continuous
    MERGE_MEASURES = Yes
    OV_ATTR = _overlaps_vertex_buffer
    TOLERANCE = 0
    LINE -> Tester_4
Tester_4
    BOOL_OP = AND
    COMPOSITE_TEST = 1 AND 2
    TEST_CLAUSE:
      TEST @Value(_x) = @Value(_closest_base_x)
      TEST @Value(_y) = @Value(_closest_base_y)
    TEST_MODE = TEST
    PASSED -> VertexCreator_2
    FAILED -> VertexCreator_3
VertexCreator_2
    INDEX = 0
    MEASURE_TYPE = Continuous
    MISSING_VAL_MODE = Compute
    MODE_NAME = Insert Point At Index
    XVAL = @Value(_closest_base_x)
    YVAL = @Value(_closest_base_y)
    -> VertexCreator_2_Output
VertexCreator_2_Output: Inspector
VertexCreator_3
    MEASURE_TYPE = Continuous
    MISSING_VAL_MODE = Compute
    MODE_NAME = Add Point
    XVAL = @Value(_closest_candidate_x)
    YVAL = @Value(_closest_candidate_y)
    -> VertexCreator_3_Output
VertexCreator_3_Output: Inspector
NeighborFinder_MatchedBase: Inspector
NeighborFinder_UnmatchedBase: Inspector
NeighborFinder_UnmatchedCandidate: Inspector
VertexCreator
    MEASURE_TYPE = Continuous
    MISSING_VAL_MODE = Compute
    MODE_NAME = Add Point
    XVAL = @Value(_closest_candidate_x)
    YVAL = @Value(_closest_candidate_y)
    -> VertexCreator_Output
    -> PointOnLineOverlayer_3 [LINE]
VertexCreator_Output: Inspector
PointOnLineOverlayer_3
    CANDIDATE_LIST_ATTRS_TO_INCLUDE_MODE = All Attributes
    CANDIDATE_LIST_NAME = point
    DEAGGREGATE_INPUT = Yes
    MEASURE_TYPE = Continuous
    MERGE_MEASURES = Yes
    OV_ATTR = _overlaps_point
    TOLERANCE = 0
    LINE -> Tester_2
Tester_2
    BOOL_OP = OR
    COMPOSITE_TEST = 1
    TEST_CLAUSE = TEST @Value(point{0}.UUID) != @Value(point{1}.UUID)
    TEST_MODE = TEST
    PASSED -> PointOnLineOverlayer_3_Line
    PASSED -> Aggregator
    PASSED -> AttributeKeeper_3
    FAILED -> Tester_2_Failed
PointOnLineOverlayer_3_Line: Inspector
Aggregator [off]
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> Deaggregator_2
Deaggregator_2
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> NetworkFlowOrientor_2 [LINE]
Tester_2_Failed: Inspector
AttributeKeeper_3
    KEEP_ATTRS = ID,UUID,Z
    -> AttributeCreator_2
AttributeCreator_2
    ATTR_TABLE:
      SET_TO UUID = @UUID()
      SET_TO comprimento = @Length()
    -> curvas_partdas (writer OGCGEOPACKAGE_2)
    -> Tester_3
    -> Aggregator_2
Aggregator_2
    ACCUM_ATTRS_NAME = Use Attributes From One Feature
    AGGREGATE_TYPE = Homogeneous Collection (If Possible)
    GROUP_BY = Z
    MODE = Geometry - Assemble One Level
    SEP = ,
    AGGREGATE -> Bufferer_2
Bufferer_2
    ANGLE = 22.5
    CAP_STYLE = Arc
    CORNER_STYLE = Arc
    MODE = AREA
    OFFSET = 0.1
    OFFSET_UNITS = NONE
    PRECISION = APPROX
    BUFFERED -> Dissolver_2
    BUFFERED -> Bufferer_2_Buffered
Dissolver_2
    ACCUM_INPUT_ATTRS = Use Attributes From One Feature
    CLEANING_TOLERANCE = Automatic
    CONNECT_Z_MODE = First Wins
    DEAGGREGATE_INPUT = Yes
    DIS_ATTR = count_dissolver
    GROUP_BY = Z
    AREA -> Clipper_2 [CLIPPER]
    AREA -> Dissolver_2_Area
    AREA -> CenterLineReplacer
    AREA -> CenterLineReplacer_2
    AREA -> CenterLineReplacer_3
Dissolver_2_Area: Inspector
CenterLineReplacer
    MODE = Approximate Center Line
    CENTERLINE -> CenterLineReplacer_Centerline
CenterLineReplacer_Centerline: Inspector
CenterLineReplacer_2
    MODE = Medial Axis
    CENTERLINE -> CenterLineReplacer_2_Centerline
CenterLineReplacer_2_Centerline: Inspector
CenterLineReplacer_3
    MODE = Straight Skeleton
    CENTERLINE -> CenterLineReplacer_3_Centerline
CenterLineReplacer_3_Centerline: Inspector
Bufferer_2_Buffered: Inspector
Tester_3 [off]
    BOOL_OP = OR
    COMPOSITE_TEST = 1
    TEST_CLAUSE = TEST @Value(comprimento) >= 5
    TEST_MODE = TEST
    PASSED -> curvas_partidas
    PASSED -> Orientor
curvas_partidas: Inspector
Orientor [off]
    FLIP_APPEARANCES_CHOICE = No
    KIND = REVERSE
    ORIENTED -> LineCombiner_3
LineCombiner_3 [off]
    ACCUM_ATTRS_NAME = Merge Incoming Attributes
    BREAK = no
    BREAK_CONNECTION_ATTRIBUTES = Z
    CONNECT_Z_MODE = First Wins
    CONSIDER_NODE_ELEVATION = no
    DEAGGREGATE_GEOMETRY = Deaggregate
    JUNCTIONS_IGNORE_ATTRIBUTES = Yes
    LINES_AS_SEGMENTS = No
    PRESERVE = no
    TOPOLOGY = End noded
    LINE -> LineCombiner_3_Line
LineCombiner_3_Line: Inspector
curvas_partdas (writer OGCGEOPACKAGE_2) [off]
    attributes: UUID text, comprimento text(200), Z double, ID int
Tester_Failed: Inspector
Intersector_Node: Inspector
Dissolver
    ACCUM_INPUT_ATTRS = Use Attributes From One Feature
    CLEANING_TOLERANCE = Automatic
    CONNECT_Z_MODE = First Wins
    DEAGGREGATE_INPUT = Yes
    AREA -> Dissolver_Area
    AREA -> Clipper_2 [CLIPPEE]
Clipper_2 [off]
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Clipper_2_Inside
    OUTSIDE -> Clipper_2_Outside
Clipper_2_Inside: Inspector
Clipper_2_Outside: Inspector
Dissolver_Area: Inspector
NetworkFlowOrientor [off]
    DIRECTION_ATTR = _direction
Creator [off]
    GEOM = <?xml version="1.0" encoding="US_ASCII" standalone="no" ?><geometry><point><coord x="0" y="0"/></point></geometry>
    GEOMTYPE = Geometry Object
    NUM = 1
    CREATED -> Creator_Created
    CREATED -> NetworkFlowOrientor_2 [DESTINATION]
NetworkFlowOrientor_2
    DIRECTION_ATTR = _direction
    NETWORK -> LineCombiner_2
    UNUSED -> LineCombiner_2
LineCombiner_2
    ACCUM_ATTRS_NAME = Merge Incoming Attributes
    BREAK = no
    BREAK_CONNECTION_ATTRIBUTES = Z ID
    CONNECT_Z_MODE = First Wins
    CONSIDER_NODE_ELEVATION = no
    DEAGGREGATE_GEOMETRY = Deaggregate
    JUNCTIONS_IGNORE_ATTRIBUTES = Yes
    LINES_AS_SEGMENTS = No
    PRESERVE = no
    TOPOLOGY = End noded
    LINE -> AttributeKeeper_2
    <REJECTED> -> LineCombiner_2__Rejected_
AttributeKeeper_2
    KEEP_ATTRS = ID,UUID,Z
    -> LineCombiner_2_Line
    -> TopologyBuilder
LineCombiner_2_Line: Inspector
TopologyBuilder [off]
    ALLOW_CYCLES = No
    BOUNDING_EDGES = All
    CLEANING_TOLERANCE = Automatic
    DEAGGREGATE_INPUT = Yes
    GENERATION_MODE = INTERSECT
    MAX = 0
    OVERLAPPING_MODE = No
    NODE -> TopologyBuilder_Node
    LINE -> TopologyBuilder_Edge
    LINE -> LineCombiner
    AREA -> TopologyBuilder_Face
TopologyBuilder_Node: Inspector
TopologyBuilder_Edge: Inspector
TopologyBuilder_Face: Inspector
LineCombiner
    ACCUM_ATTRS_NAME = Use Attributes From One Feature
    BREAK = no
    BREAK_CONNECTION_ATTRIBUTES = ID Z
    CONNECT_Z_MODE = First Wins
    CONSIDER_NODE_ELEVATION = no
    DEAGGREGATE_GEOMETRY = Deaggregate
    JUNCTIONS_IGNORE_ATTRIBUTES = Yes
    LINES_AS_SEGMENTS = No
    PRESERVE = no
    TOPOLOGY = Vertex noded
    LINE -> LineCombiner_Line
LineCombiner_Line: Inspector
LineCombiner_2__Rejected_: Inspector
Creator_Created: Inspector [off]
Generalizer [off]
    ALG_TEXT = Douglas (Generalize)
    PRESERVE = No
    PRESERVE_PATHS = No
    TOLERANCE = 5
curvas_nivel (writer OGCGEOPACKAGE_1) [off]
