FME workspace GOTHIC_TESTES.fmw

Parameters:
- SourceDataset_MDB_ADO = $(FME_MF_DIR)mdb\b_sirgas_utm.mdb   # Source Microsoft Access Database File(s)
- SourceDataset_MDB_ADO_3 = $(FME_MF_DIR)mdb\b_sirgas_utm.mdb   # Source Microsoft Access Database File(s)
- FEATURE_TYPES = Veg_Cultivada_SHAPE_Index Veg_Cultivada Trilha_Picada_SHAPE_Index Trilha_Picada Trecho_Rodoviario_SHAPE_Index Trecho_Rodoviario Trecho_Massa_Dagua_SHAPE_Index Trecho_Massa_Dagua Trecho_Energia_SHAPE_Index Trecho_Energia Trecho_Duto_SHAPE_Index Trecho_Duto Trecho_Drenagem_SHAPE_Index Trecho_Drenagem Travessia_point_SHAPE_Index Travessia_point Torre_Comunic_SHAPE_Index Torre_Comunic Terreno_Suj_Inundacao_SHAPE_Index Terreno_Suj_Inundacao Terreno_Exposto_SHAPE_Index Terreno_Exposto T_1_PolyErrors_Shape_Index T_1_PolyErrors T_1_PointErrors_Shape_Index T_1_PointErrors T_1_LineErrors_Shape_Index T_1_LineErrors T_1_DirtyAreas_DirtyArea_Index T_1_DirtyAreas Sumidouro_Vertedouro_SHAPE_Index Sumidouro_Vertedouro Selections SelectedObjects Rocha_polygon_SHAPE_Index Rocha_polygon Pto_Est_Med_Fenomenos_SHAPE_Index Pto_Est_Med_Fenomenos Posto_Combustivel_point_SHAPE_Index Posto_Combustivel_point Ponto_Trecho_Energia_SHAPE_Index Ponto_Trecho_Energia Ponto_Rodoviario_Ferrov_SHAPE_Index Ponto_Rodoviario_Ferrov Ponto_Inicio_Drenagem_SHAPE_Index Ponto_Inicio_Drenagem Ponto_Duto_SHAPE_Index Ponto_Duto Ponto_Drenagem_SHAPE_Index Ponto_Drenagem Ponto_Cotado_Altimetrico_SHAPE_Index Ponto_Cotado_Altimetrico Ponte_point_SHAPE_Index Ponte_point Pista_Ponto_Pouso_polygon_SHAPE_Index Pista_Ponto_Pouso_polygon Pista_Competicao_line_SHAPE_Index Pista_Competicao_line Patio_polygon_SHAPE_Index Patio_polygon Nome_Local_SHAPE_Index Nome_Local Massa_Dagua_SHAPE_Index Massa_Dagua Limite_Massa_Dagua_SHAPE_Index Limite_Massa_Dagua Ilha_polygon_SHAPE_Index Ilha_polygon Identific_Trecho_Rod_SHAPE_Index Identific_Trecho_Rod Gruta_Caverna_point_SHAPE_Index Gruta_Caverna_point Grupo_Transform_Energ_point_SHAPE_Index Grupo_Transform_Energ_point GDB_SpatialRefs GDB_ReplicaLog GDB_ItemTypes GDB_Items_Shape_Index GDB_Items GDB_ItemRelationshipTypes GDB_ItemRelationships GDB_GeomColumns GDB_DatabaseLocks GDB_ColumnInfo Galeria_Bueiro_point_SHAPE_Index Galeria_Bueiro_point Fonte_Dagua_SHAPE_Index Fonte_Dagua Est_Gerad_Energia_Eletr_polygon_SHAPE_Index Est_Gerad_Energia_Eletr_polygon Entroncamento_SHAPE_Index Entroncamento Elemento_Fisiog_Natural_point_SHAPE_Index Elemento_Fisiog_Natural_point Elemento_Fisiog_Natural_line_SHAPE_Index Elemento_Fisiog_Natural_line Edif_Servico_Social_polygon_SHAPE_Index Edif_Servico_Social_polygon Edif_Servico_Social_point_SHAPE_Index Edif_Servico_Social_point Edif_Saude_polygon_SHAPE_Index Edif_Saude_polygon Edif_Saude_point_SHAPE_Index Edif_Saude_point Edif_Saneamento_point_SHAPE_Index Edif_Saneamento_point Edif_Rodoviaria_polygon_SHAPE_Index Edif_Rodoviaria_polygon Edif_Rodoviaria_point_SHAPE_Index Edif_Rodoviaria_point Edif_Religiosa_polygon_SHAPE_Index Edif_Religiosa_polygon Edif_Religiosa_point_SHAPE_Index Edif_Religiosa_point Edif_Pub_Militar_polygon_SHAPE_Index Edif_Pub_Militar_polygon Edif_Pub_Militar_point_SHAPE_Index Edif_Pub_Militar_point Edif_Pub_Civil_polygon_SHAPE_Index Edif_Pub_Civil_polygon Edif_Pub_Civil_point_SHAPE_Index Edif_Pub_Civil_point Edif_Industrial_polygon_SHAPE_Index Edif_Industrial_polygon Edif_Industrial_point_SHAPE_Index Edif_Industrial_point Edif_Habitacional_point_SHAPE_Index Edif_Habitacional_point Edif_Ext_Mineral_polygon_SHAPE_Index Edif_Ext_Mineral_polygon Edif_Ext_Mineral_point_SHAPE_Index Edif_Ext_Mineral_point Edif_Ensino_polygon_SHAPE_Index Edif_Ensino_polygon Edif_Ensino_point_SHAPE_Index Edif_Ensino_point Edif_Constr_Est_Med_point_SHAPE_Index Edif_Constr_Est_Med_point Edif_Const_Turistica_point_SHAPE_Index Edif_Const_Turistica_point Edif_Const_Lazer_polygon_SHAPE_Index Edif_Const_Lazer_polygon Edif_Const_Lazer_point_SHAPE_Index Edif_Const_Lazer_point Edif_Const_Aeroportuaria_point_SHAPE_Index Edif_Const_Aeroportuaria_point Edif_Comunic_point_SHAPE_Index Edif_Comunic_point Edif_Comerc_Serv_polygon_SHAPE_Index Edif_Comerc_Serv_polygon Edif_Comerc_Serv_point_SHAPE_Index Edif_Comerc_Serv_point Edif_Agrop_Ext_Veg_Pesca_point_SHAPE_Index Edif_Agrop_Ext_Veg_Pesca_point Edif_Abast_Agua_point_SHAPE_Index Edif_Abast_Agua_point Deposito_Geral_polygon_SHAPE_Index Deposito_Geral_polygon Deposito_Geral_point_SHAPE_Index Deposito_Geral_point Dep_Saneamento_polygon_SHAPE_Index Dep_Saneamento_polygon Dep_Saneamento_point_SHAPE_Index Dep_Saneamento_point Dep_Abast_Agua_point_SHAPE_Index Dep_Abast_Agua_point Delimitacao_Fisica_SHAPE_Index Delimitacao_Fisica Curva_Nivel_SHAPE_Index Curva_Nivel Confluencia_SHAPE_Index Confluencia Comporta_line_SHAPE_Index Comporta_line Cidade_SHAPE_Index Cidade Cerrado_Cerradao_SHAPE_Index Cerrado_Cerradao Cemiterio_polygon_SHAPE_Index Cemiterio_polygon Cemiterio_point_SHAPE_Index Cemiterio_point Campo_SHAPE_Index Campo_Quadra_polygon_SHAPE_Index Campo_Quadra_polygon Campo_Quadra_point_SHAPE_Index Campo_Quadra_point Campo Caatinga_SHAPE_Index Caatinga Barragem_line_SHAPE_Index Barragem_line Banco_Areia_polygon_SHAPE_Index Banco_Areia_polygon Atracadouro_polygon_SHAPE_Index Atracadouro_polygon Atracadouro_point_SHAPE_Index Atracadouro_point Arruamento_SHAPE_Index Arruamento Arquibancada_point_SHAPE_Index Arquibancada_point Area_Uso_Comunitario_point_SHAPE_Index Area_Uso_Comunitario_point Area_Lazer_SHAPE_Index Area_Lazer Area_Industrial_SHAPE_Index Area_Industrial Area_Ext_Mineral_SHAPE_Index Area_Ext_Mineral Area_Energia_Eletrica_SHAPE_Index Area_Energia_Eletrica Area_Edificada_SHAPE_Index Area_Edificada Antena_Comunic_SHAPE_Index Antena_Comunic Alter_Fisiog_Antropica_line_SHAPE_Index Alter_Fisiog_Antropica_line Aglomerado_Rural_SHAPE_Index Aglomerado_Rural
- DestDataset_MDB_ADO = $(FME_MF_DIR)mdb\b_sirgas_utm_nomeAbrev.mdb   # Destination Microsoft Access Database File
- DestDataset_MDB_ADO_2 = $(FME_MF_DIR)mdb\b_sirgas_utm_nomeAbrev.mdb   # Destination Microsoft Access Database File

Readers:
- MDB_ADO_1: MDB_ADO from $(SourceDataset_MDB_ADO)
- MDB_ADO_2: MDB_ADO from $(SourceDataset_MDB_ADO_3)

Writers:
- MDB_ADO_3: MDB_ADO to $(DestDataset_MDB_ADO)
- MDB_ADO_4: MDB_ADO to $(DestDataset_MDB_ADO_2)

AttributeFilter [off]
    ATTR_NAME = nomeAbrev
    ATTR_VALUES = <EMPTY>,<MISSING>,<NULL>,<UNFILTERED>
Note: B_SIRGAS_UTM MDB
Veg_Cultivada_SHAPE_Index (reader MDB_ADO_2) [off]
    attributes: IndexedObjectId long, MinGX long, MinGY long, MaxGX long, MaxGY long, ExtentRight double, OriginClassID long, nomeAbrev text(255), tipoEdifAero long, nrPistas long, tipoCemiterio long, FieldName text(255), IsRetired long, MUnits double, MLow double, fkComplDuto text(255), DirtyArea oleobject, SRTEXT memo, TargetGen long, tipoResiduo long, tipoAglomerado long, SHAPE oleobject, LockID autonumber, nrDutos long, ZUnits double, ExtentTop double, tipoDivisaoCnae long, relacionado long, ZLow double, fkComplEstrApoio text(255),
      offSetY single, classificacaoPorte long, tipoEdifAgropec long, salinidade long, posicaoPista long, causa long, denominacaoAssociada long, longitude_txt text(255), nrFaixas long, tamanhoTxt single, tipoConteudo long, IdxOriginY double, situacaoEspacial long, tipoEdifRod long, tipoTrechoRod long, situacaoEmAgua long, tensaoEletrica single, tipoTerrExp long, tipoEdifTurist long, vaoLivreHoriz single, fkComplOrgEnsino text(255), DatasetSubtype1 long, velocidadeMedCorrente single, XYTolerance double, jurisdicao long, SourceBeginGen long, tipoUsoEdif long, Type replicationid, tipoEstGerad long, DirtyArea_Length double,
      repTipoTxt long, fkComplRodovia text(255), DatasetSubtype2 long, pesoMaxSuportTon single, causaExposicao long, HasM yesno, FalseM double, tipoDepAbast long, potenciaFiscalizadaKW single, DestID long, escalaMaxSimbolizar long, IdxOriginX double, OrigItemTypeID replicationid, operacional long, simbolizar integer, Defaults oleobject, matTransp long, tipoEdif long, tipoExposicao long, DatasetInfo1 text(255), destEnergElet long, simbolizarCartaMini integer, indice long, tipoAreaUsoComun long, Shape oleobject, emDuto long, ReplicaID long, terreno long, fkComplIndustria text(255), denso long,
      canteiroDivisorio long, tipoEdifLazer long, coincideComDentroDe long, dentroDePoligono long, ShapeType long, tipoCampo long, tipoBanco long, SHAPE_Area double, tipoLimMassa long, homologacao long, especie long, fkComplOrgAgrop text(255), alturaEstimada single, latitude single, tipoPonte long, larguraMedia single, nome text(255), BackwardLabel text(255), codigoEstacao text(255), modalidade long, IsContainment integer, situacaoAgua long, tipoPtoEnergia long, controleId text(255), ExtentBottom double, setor long, qualidAgua long, tipoEdifComunic long, orientacao single, fkComplEstMedFen text(255),
      MachineName memo, latitude_txt text(255), tipoElemNat long, tipoDelimFis long, ZHigh double, fkComplPubCivil text(255), fkClassificador text(255), SelectionID autonumber, TableName text(255), controle_id text(200), valorVolume single, construcao long, matConstr long, tipoPista long, profundidadeMedia single, revestimento long, ovgd long, DirtyArea_Area double, tipoCampoQuadra long, ParentTypeID replicationid, XYUnits double, OriginID long, tipoAtracad long, tipoDepSaneam long, cota long, fkComplSvSoc text(255), tipoCerr long, largura single, fkComplOrgRel text(255), modalUso long,
      periodicidadeInunda text(255), Name text(160), tipoLavoura long, Attributes memo, ordemTickDepressao long, necessidadeManutencao long, religiao text(255), espacamentoIndividuos single, tipoPtoEstMed long, espessuraDAP single, tipoEdifRelig long, tipoTravessia long, FalseZ double, tipoDepGeral long, Shape_Area double, ID autonumber, ExtentLeft double, tipoSumVert long, Properties long, fkComplComunic text(255), unidadeVolume long, fkComplAbsAgua text(255), emMassaDagua long, IdxGridSize double, ErrorCode long, UserName memo, fkComplTrCurDagua text(255), orgaoEnteResp text(255), MTolerance double, fkComplPortuario text(255),
      eixoPrincipal long, fkComplHabit text(255), tipoTrechoDuto long, IsHighPrecision long, tipoFonteDagua long, justTxt long, tipoProdutoResiduo long, tipoEntroncamento long, ocorrenciaEm long, velocidadeMedia long, sigla text(255), Shape_Length double, PhysicalName text(160), eletrificada long, OBJECTID autonumber, regime long, fkComplLazer text(255), administracao long, TargetName text(255), ZTolerance double, tipoEdifSaneam long, cultivoPredominante long, Event long, caladoMax single, tipoEdifAbast long, ForwardLabel text(255), FalseY double, SHAPE_Length double, codEstacao text(255), fkComplSubEnEletr text(255),
      FalseX double, Documentation memo, cotaComprovada long, offSet single, situacaoFisica long, chamine long, compartilhado long, DestClassID long, extensao single, Path memo, antropizada long, HasZ yesno, offSetSimbY single, nascente long, fkComplAeroport text(255), posicaoRelativa long, longitude single, alturaMediaMargem single, fkComplMilitar text(255), usoPista long, IsException long, LogDate datetime, fkComplOrgExtMin text(255), tipoClasseCnae long, navegabilidade long, LockType long, vaoVertical single, fkComplGerEnEletr text(255), fkComplOrgComSv text(255), UUID replicationid,
      tipoAlterAntrop long, TopoRuleID long, geometriaAproximada long, cotadaPorProcesso long, columnFlags long, usoPrincipal long, depressao long, offSetX single, nivelAtencao long, SRID autonumber, identificadorPosicGeo text(255), offSetSimbX single, ObjectID autonumber, trafego long, DestItemTypeID replicationid, URL text(255), codTrechoRodov text(255), tipoEdifComercServ long, materialPredominante long, Definition memo, fkComplSaneam text(255), tratamento long, fkComplSaude text(255), residuo long, posicaoRelEdific long, ensino long, alturaMediaIndividuos single, MHigh double, potenciaOutorgadaKW single, obsAquisicao text(255),
      tipoMassaDagua long, TopoRuleType long, numCircuitos long, SourceEndGen long, tipoCidade long, visivel long, concessionaria text(255), finalidade long, ItemInfo memo, DatasetInfo2 text(255)
    -> _All_
_All_: Inspector
Dep_Abast_Agua_point (reader MDB_ADO_1)
    attributes: OBJECTID autonumber, SHAPE oleobject, simbolizarCartaMini integer, justTxt long, offSetY single, fkComplOrgExtMin text(255), fkComplOrgComSv text(255), offSetX single, fkComplIndustria text(255), controleId text(255), construcao long, fkComplAbsAgua text(255), orientacao single, nomeAbrev text(255), finalidade long, offSetSimbY single, fkComplOrgAgrop text(255), escalaMaxSimbolizar long, fkClassificador text(255), operacional long, geometriaAproximada long, obsAquisicao text(255), situacaoFisica long, situacaoAgua long, tipoDepAbast long, nome text(255), offSetSimbX single, matConstr long, controle_id text(200)
    -> Tester
Tester
    BOOL_OP = OR
    TEST_DESCRIPTION = ""
    TEST_MODE = Automatic
    TEST_CLAUSE = TEST nomeAbrev ATTRIBUTE_VALUE_NULL ""
    PASSED -> AttributeCreator
AttributeCreator
    ATTR_LIST = nomeAbrev,Caixa d'água
    -> Dep_Abast_Agua_point (writer MDB_ADO_4)
Dep_Abast_Agua_point (writer MDB_ADO_4)
    attributes: OBJECTID autonumber, SHAPE oleobject, simbolizarCartaMini integer, justTxt long, offSetY single, fkComplOrgExtMin text(255), fkComplOrgComSv text(255), offSetX single, fkComplIndustria text(255), controleId text(255), construcao long, fkComplAbsAgua text(255), orientacao single, nomeAbrev text(255), finalidade long, offSetSimbY single, fkComplOrgAgrop text(255), escalaMaxSimbolizar long, fkClassificador text(255), operacional long, geometriaAproximada long, obsAquisicao text(255), situacaoFisica long, situacaoAgua long, tipoDepAbast long, nome text(255), offSetSimbX single, matConstr long, controle_id text(200)

Bookmark: mdb
Trecho_Energia_SHAPE_Index (reader MDB_ADO_1) [off]
    attributes: IndexedObjectId long, MinGX long, MinGY long, MaxGX long, MaxGY long
    -> AttributeFilter
Trecho_Drenagem (reader MDB_ADO_1) [off]
    attributes: OBJECTID autonumber, SHAPE oleobject, geometriaAproximada long, dentroDePoligono long, nome text(255), caladoMax single, navegabilidade long, fkComplTrCurDagua text(255), nomeAbrev text(255), compartilhado long, larguraMedia single, velocidadeMedCorrente single, regime long, profundidadeMedia single, simbolizarCartaMini integer, coincideComDentroDe long, eixoPrincipal long, obsAquisicao text(255), controleId text(255), fkClassificador text(255), controle_id text(200), SHAPE_Length double
    -> AttributeFilter
Rocha_polygon_SHAPE_Index (reader MDB_ADO_1) [off]
    attributes: IndexedObjectId long, MinGX long, MinGY long, MaxGX long, MaxGY long
    -> AttributeFilter
Travessia_point_SHAPE_Index (reader MDB_ADO_1) [off]
    attributes: IndexedObjectId long, MinGX long, MinGY long, MaxGX long, MaxGY long
    -> AttributeFilter
Area_Uso_Comunitario_point (reader MDB_ADO_1) [off]
    attributes: OBJECTID autonumber, SHAPE oleobject, controleId text(255), tamanhoTxt single, justTxt long, offSetY single, tipoAreaUsoComun long, nomeAbrev text(255), geometriaAproximada long, simbolizarCartaMini integer, nome text(255), offSetX single, obsAquisicao text(255), fkClassificador text(255), controle_id text(200)
    -> AttributeFilter
Ponto_Inicio_Drenagem (reader MDB_ADO_1) [off]
    attributes: OBJECTID autonumber, SHAPE oleobject, controleId text(255), justTxt long, geometriaAproximada long, simbolizarCartaMini integer, fkClassificador text(255), obsAquisicao text(255), nomeAbrev text(255), nascente long, offSetY single, offSetX single, nome text(255), controle_id text(200)
    -> AttributeFilter
Edif_Saude_point_SHAPE_Index (reader MDB_ADO_1) [off]
    attributes: IndexedObjectId long, MinGX long, MinGY long, MaxGX long, MaxGY long
    -> AttributeFilter
Deposito_Geral_polygon_SHAPE_Index (reader MDB_ADO_1) [off]
    attributes: IndexedObjectId long, MinGX long, MinGY long, MaxGX long, MaxGY long
    -> AttributeFilter
Rocha_polygon (reader MDB_ADO_1) [off]
    attributes: OBJECTID autonumber, SHAPE oleobject, controleId text(255), tamanhoTxt single, justTxt long, tipoElemNat long, offSetY single, nomeAbrev text(255), geometriaAproximada long, simbolizarCartaMini integer, nome text(255), offSetX single, obsAquisicao text(255), fkClassificador text(255), controle_id text(200), SHAPE_Length double, SHAPE_Area double
    -> AttributeFilter
Campo_SHAPE_Index (reader MDB_ADO_1) [off]
    attributes: IndexedObjectId long, MinGX long, MinGY long, MaxGX long, MaxGY long
    -> AttributeFilter
Campo_Quadra_point_SHAPE_Index (reader MDB_ADO_1) [off]
    attributes: IndexedObjectId long, MinGX long, MinGY long, MaxGX long, MaxGY long
    -> AttributeFilter
Alter_Fisiog_Antropica_line (reader MDB_ADO_1) [off]
    attributes: OBJECTID autonumber, SHAPE oleobject, obsAquisicao text(255), fkClassificador text(255), controleId text(255), justTxt long, offSet single, offSetY single, nomeAbrev text(255), tipoAlterAntrop long, geometriaAproximada long, nome text(255), offSetX single, simbolizarCartaMini integer, controle_id text(200), SHAPE_Length double
    -> AttributeFilter
Edif_Agrop_Ext_Veg_Pesca_point_SHAPE_Index (reader MDB_ADO_1) [off]
    attributes: IndexedObjectId long, MinGX long, MinGY long, MaxGX long, MaxGY long
    -> AttributeFilter
Atracadouro_polygon (reader MDB_ADO_1) [off]
    attributes: OBJECTID autonumber, SHAPE oleobject, geometriaAproximada long, offSetSimbX single, orientacao single, fkComplPortuario text(255), nome text(255), offSetY single, justTxt long, offSetX single, offSetSimbY single, nomeAbrev text(255), administracao long, matConstr long, operacional long, simbolizarCartaMini integer, tipoAtracad long, obsAquisicao text(255), controleId text(255), situacaoFisica long, escalaMaxSimbolizar long, fkClassificador text(255), controle_id text(200), SHAPE_Length double, SHAPE_Area double
    -> AttributeFilter
Edif_Rodoviaria_polygon (reader MDB_ADO_1) [off]
    attributes: OBJECTID autonumber, SHAPE oleobject, geometriaAproximada long, offSetSimbX single, orientacao single, nome text(255), offSetY single, justTxt long, offSetX single, offSetSimbY single, tipoEdifRod long, administracao long, nomeAbrev text(255), matConstr long, operacional long, simbolizarCartaMini integer, fkComplEstrApoio text(255), obsAquisicao text(255), controleId text(255), situacaoFisica long, escalaMaxSimbolizar long, fkClassificador text(255), controle_id text(200), SHAPE_Length double, SHAPE_Area double
    -> AttributeFilter
Trecho_Rodoviario (reader MDB_ADO_1) [off]
    attributes: OBJECTID autonumber, SHAPE oleobject, geometriaAproximada long, revestimento long, nrPistas long, trafego long, nome text(255), offSet single, sigla text(255), administracao long, velocidadeMedia long, nrFaixas long, operacional long, codTrechoRodov text(255), concessionaria text(255), simbolizarCartaMini integer, canteiroDivisorio long, fkComplRodovia text(255), tipoTrechoRod long, obsAquisicao text(255), controleId text(255), pesoMaxSuportTon single, jurisdicao long, escalaMaxSimbolizar long, situacaoFisica long, fkClassificador text(255), controle_id text(200), SHAPE_Length double
    -> AttributeFilter
Delimitacao_Fisica (reader MDB_ADO_1) [off]
    attributes: OBJECTID autonumber, SHAPE oleobject, tipoDelimFis long, obsAquisicao text(255), controleId text(255), fkClassificador text(255), justTxt long, matConstr long, escalaMaxSimbolizar long, offSetY single, nomeAbrev text(255), geometriaAproximada long, eletrificada long, nome text(255), offSetX single, simbolizarCartaMini integer, controle_id text(200), SHAPE_Length double
    -> AttributeFilter
Ponto_Duto (reader MDB_ADO_1) [off]
    attributes: OBJECTID autonumber, SHAPE oleobject, obsAquisicao text(255), fkClassificador text(255), simbolizarCartaMini integer, geometriaAproximada long, controleId text(255), relacionado long, controle_id text(200)
    -> AttributeFilter
Trecho_Massa_Dagua_SHAPE_Index (reader MDB_ADO_1) [off]
    attributes: IndexedObjectId long, MinGX long, MinGY long, MaxGX long, MaxGY long
    -> AttributeFilter
Edif_Const_Lazer_point_SHAPE_Index (reader MDB_ADO_1) [off]
    attributes: IndexedObjectId long, MinGX long, MinGY long, MaxGX long, MaxGY long
    -> AttributeFilter
Antena_Comunic (reader MDB_ADO_1) [off]
    attributes: OBJECTID autonumber, SHAPE oleobject, offSetX single, fkComplComunic text(255), justTxt long, nomeAbrev text(255), simbolizarCartaMini integer, controleId text(255), offSetSimbY single, nome text(255), escalaMaxSimbolizar long, posicaoRelEdific long, offSetSimbX single, obsAquisicao text(255), fkClassificador text(255), offSetY single, geometriaAproximada long, controle_id text(200)
    -> AttributeFilter
T_1_PolyErrors (reader MDB_ADO_1) [off]
    attributes: ObjectID autonumber, OriginClassID long, OriginID long, DestClassID long, DestID long, TopoRuleType long, TopoRuleID long, Shape oleobject, IsException long, Shape_Length double, Shape_Area double
    -> AttributeFilter
Barragem_line_SHAPE_Index (reader MDB_ADO_1) [off]
    attributes: IndexedObjectId long, MinGX long, MinGY long, MaxGX long, MaxGY long
    -> AttributeFilter
Arruamento (reader MDB_ADO_1) [off]
    attributes: OBJECTID autonumber, SHAPE oleobject, revestimento long, obsAquisicao text(255), controleId text(255), nrFaixas long, situacaoFisica long, fkClassificador text(255), trafego long, escalaMaxSimbolizar long, nomeAbrev text(255), geometriaAproximada long, simbolizarCartaMini integer, nome text(255), operacional long, canteiroDivisorio long, controle_id text(200), SHAPE_Length double
    -> AttributeFilter
Edif_Comerc_Serv_polygon_SHAPE_Index (reader MDB_ADO_1) [off]
    attributes: IndexedObjectId long, MinGX long, MinGY long, MaxGX long, MaxGY long
    -> AttributeFilter
Edif_Pub_Militar_polygon_SHAPE_Index (reader MDB_ADO_1) [off]
    attributes: IndexedObjectId long, MinGX long, MinGY long, MaxGX long, MaxGY long
    -> AttributeFilter
Trecho_Energia (reader MDB_ADO_1) [off]
    attributes: OBJECTID autonumber, SHAPE oleobject, especie long, posicaoRelativa long, tensaoEletrica single, situacaoFisica long, nomeAbrev text(255), numCircuitos long, simbolizarCartaMini integer, controleId text(255), nome text(255), emDuto long, operacional long, escalaMaxSimbolizar long, obsAquisicao text(255), fkClassificador text(255), geometriaAproximada long, controle_id text(200), SHAPE_Length double
    -> AttributeFilter
Edif_Const_Turistica_point (reader MDB_ADO_1) [off]
    attributes: OBJECTID autonumber, SHAPE oleobject, geometriaAproximada long, offSetSimbX single, orientacao single, ovgd long, nome text(255), fkComplLazer text(255), offSetY single, justTxt long, offSetX single, offSetSimbY single, nomeAbrev text(255), matConstr long, operacional long, tipoEdifTurist long, simbolizarCartaMini integer, obsAquisicao text(255), controleId text(255), situacaoFisica long, escalaMaxSimbolizar long, fkClassificador text(255), controle_id text(200)
    -> AttributeFilter
Cemiterio_polygon (reader MDB_ADO_1) [off]
    attributes: OBJECTID autonumber, SHAPE oleobject, geometriaAproximada long, offSetSimbX single, orientacao single, nome text(255), offSetY single, justTxt long, denominacaoAssociada long, offSetX single, offSetSimbY single, nomeAbrev text(255), tipoCemiterio long, simbolizarCartaMini integer, obsAquisicao text(255), controleId text(255), escalaMaxSimbolizar long, fkClassificador text(255), controle_id text(200), SHAPE_Length double, SHAPE_Area double
    -> AttributeFilter
Caatinga (reader MDB_ADO_1) [off]
    attributes: OBJECTID autonumber, SHAPE oleobject, controleId text(255), alturaMediaIndividuos single, geometriaAproximada long, simbolizarCartaMini integer, fkClassificador text(255), obsAquisicao text(255), classificacaoPorte long, nomeAbrev text(255), denso long, antropizada long, nome text(255), controle_id text(200), SHAPE_Length double, SHAPE_Area double
    -> AttributeFilter
Dep_Saneamento_polygon (reader MDB_ADO_1) [off]
    attributes: OBJECTID autonumber, SHAPE oleobject, fkComplSaneam text(255), geometriaAproximada long, fkClassificador text(255), offSetSimbX single, residuo long, orientacao single, nome text(255), offSetY single, justTxt long, offSetX single, offSetSimbY single, nomeAbrev text(255), finalidade long, construcao long, matConstr long, operacional long, simbolizarCartaMini integer, obsAquisicao text(255), controleId text(255), tipoDepSaneam long, situacaoFisica long, escalaMaxSimbolizar long, tipoResiduo long, controle_id text(200), SHAPE_Length double, SHAPE_Area double
    -> AttributeFilter
Identific_Trecho_Rod (reader MDB_ADO_1) [off]
    attributes: OBJECTID autonumber, SHAPE oleobject, fkComplRodovia text(255), nomeAbrev text(255), controleId text(255), simbolizar integer, offSet single, obsAquisicao text(255), simbolizarCartaMini integer, sigla text(255), repTipoTxt long, nome text(255), codTrechoRodov text(255), fkClassificador text(255), controle_id text(200)
    -> AttributeFilter
Arquibancada_point_SHAPE_Index (reader MDB_ADO_1) [off]
    attributes: IndexedObjectId long, MinGX long, MinGY long, MaxGX long, MaxGY long
    -> AttributeFilter
Edif_Ext_Mineral_polygon_SHAPE_Index (reader MDB_ADO_1) [off]
    attributes: IndexedObjectId long, MinGX long, MinGY long, MaxGX long, MaxGY long
    -> AttributeFilter
Trilha_Picada_SHAPE_Index (reader MDB_ADO_1) [off]
    attributes: IndexedObjectId long, MinGX long, MinGY long, MaxGX long, MaxGY long
    -> AttributeFilter
Edif_Servico_Social_polygon_SHAPE_Index (reader MDB_ADO_1) [off]
    attributes: IndexedObjectId long, MinGX long, MinGY long, MaxGX long, MaxGY long
    -> AttributeFilter
Barragem_line (reader MDB_ADO_1) [off]
    attributes: OBJECTID autonumber, SHAPE oleobject, geometriaAproximada long, orientacao single, fkComplGerEnEletr text(255), nome text(255), offSetY single, justTxt long, usoPrincipal long, offSetX single, nomeAbrev text(255), matConstr long, operacional long, simbolizarCartaMini integer, tamanhoTxt single, obsAquisicao text(255), controleId text(255), situacaoFisica long, fkClassificador text(255), controle_id text(200), SHAPE_Length double
    -> AttributeFilter
Edif_Habitacional_point (reader MDB_ADO_1) [off]
    attributes: OBJECTID autonumber, SHAPE oleobject, geometriaAproximada long, fkComplHabit text(255), offSetSimbX single, orientacao single, nome text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Edif_Const_Aeroportuaria_point_SHAPE_Index (reader MDB_ADO_1) [off]
    attributes: IndexedObjectId long, MinGX long, MinGY long, MaxGX long, MaxGY long
    -> AttributeFilter
Edif_Const_Turistica_point_SHAPE_Index (reader MDB_ADO_1) [off]
    attributes: IndexedObjectId long, MinGX long, MinGY long, MaxGX long, MaxGY long
    -> AttributeFilter
T_1_DirtyAreas (reader MDB_ADO_1) [off]
    attributes: ObjectID autonumber, IsRetired long, DirtyArea oleobject, DirtyArea_Length double, DirtyArea_Area double
    -> AttributeFilter
Atracadouro_polygon_SHAPE_Index (reader MDB_ADO_1) [off]
    attributes: IndexedObjectId long, MinGX long, MinGY long, MaxGX long, MaxGY long
    -> AttributeFilter
Cemiterio_polygon_SHAPE_Index (reader MDB_ADO_1) [off]
    attributes: IndexedObjectId long, MinGX long, MinGY long, MaxGX long, MaxGY long
    -> AttributeFilter
Caatinga_SHAPE_Index (reader MDB_ADO_1) [off]
    attributes: IndexedObjectId long, MinGX long, MinGY long, MaxGX long, MaxGY long
    -> AttributeFilter
Cemiterio_point (reader MDB_ADO_1) [off]
    attributes: OBJECTID autonumber, SHAPE oleobject, geometriaAproximada long, offSetSimbX single, orientacao single, nome text(255), offSetY single, justTxt long, denominacaoAssociada long, offSetX single, offSetSimbY single, nomeAbrev text(255), tipoCemiterio long, simbolizarCartaMini integer, obsAquisicao text(255), controleId text(255), escalaMaxSimbolizar long, fkClassificador text(255), controle_id text(200)
    -> AttributeFilter
Ponto_Trecho_Energia_SHAPE_Index (reader MDB_ADO_1) [off]
    attributes: IndexedObjectId long, MinGX long, MinGY long, MaxGX long, MaxGY long
    -> AttributeFilter
Area_Energia_Eletrica_SHAPE_Index (reader MDB_ADO_1) [off]
    attributes: IndexedObjectId long, MinGX long, MinGY long, MaxGX long, MaxGY long
    -> AttributeFilter
Sumidouro_Vertedouro_SHAPE_Index (reader MDB_ADO_1) [off]
    attributes: IndexedObjectId long, MinGX long, MinGY long, MaxGX long, MaxGY long
    -> AttributeFilter
Edif_Servico_Social_polygon (reader MDB_ADO_1) [off]
    attributes: OBJECTID autonumber, SHAPE oleobject, geometriaAproximada long, offSetSimbX single, orientacao single, tipoClasseCnae long, nome text(255), fkComplSvSoc text(255), offSetY single, justTxt long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
Edif_Constr_Est_Med_point_SHAPE_Index (reader MDB_ADO_1) [off]
    attributes: IndexedObjectId long, MinGX long, MinGY long, MaxGX long, MaxGY long
    -> AttributeFilter
Deposito_Geral_polygon (reader MDB_ADO_1) [off]
    attributes: OBJECTID autonumber, SHAPE oleobject, nome text(255), tipoExposicao long, fkComplOrgExtMin text(255), fkComplAeroport text(255), simbolizarCartaMini integer, tipoProdutoResiduo long, tipoConteudo long, valorVolume single, fkComplOrgComSv text(255), tratamento long, nomeAbrev text(255), fkComplIndustria text(255), offSetY single, operacional long, offSetSimbX single, situacaoFisica long, geometriaAproximada long, fkComplPortuario text(255), fkClassificador text(255), obsAquisicao text(255), offSetSimbY single, justTxt long, fkComplGerEnEletr text(255), fkComplOrgAgrop text(255), orientacao single, matConstr long, tipoDepGeral long, offSetX single,
      fkComplEstrApoio text(255), unidadeVolume long, controleId text(255), escalaMaxSimbolizar long, controle_id text(200), SHAPE_Length double, SHAPE_Area double
    -> AttributeFilter
GDB_ItemTypes (reader MDB_ADO_1) [off]
    attributes: ObjectID autonumber, UUID replicationid, ParentTypeID replicationid, Name text(160)
    -> AttributeFilter
Edif_Ensino_point_SHAPE_Index (reader MDB_ADO_1) [off]
    attributes: IndexedObjectId long, MinGX long, MinGY long, MaxGX long, MaxGY long
    -> AttributeFilter
Ponto_Cotado_Altimetrico (reader MDB_ADO_1) [off]
    attributes: OBJECTID autonumber, SHAPE oleobject, controleId text(255), cota long, justTxt long, geometriaAproximada long, cotaComprovada long, simbolizarCartaMini integer, fkClassificador text(255), obsAquisicao text(255), visivel long, offSetY single, offSetX single, controle_id text(200)
    -> AttributeFilter
Edif_Saude_polygon_SHAPE_Index (reader MDB_ADO_1) [off]
    attributes: IndexedObjectId long, MinGX long, MinGY long, MaxGX long, MaxGY long
    -> AttributeFilter
Edif_Pub_Militar_point_SHAPE_Index (reader MDB_ADO_1) [off]
    attributes: IndexedObjectId long, MinGX long, MinGY long, MaxGX long, MaxGY long
    -> AttributeFilter
Edif_Pub_Civil_polygon (reader MDB_ADO_1) [off]
    attributes: OBJECTID autonumber, SHAPE oleobject, geometriaAproximada long, offSetSimbX single, orientacao single, fkComplPubCivil text(255), tipoEdif long, nome text(255), offSetY single, justTxt long, tipoUsoEdif long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
Veg_Cultivada_SHAPE_Index (reader MDB_ADO_1) [off]
    attributes: IndexedObjectId long, MinGX long, MinGY long, MaxGX long, MaxGY long
    -> AttributeFilter
Veg_Cultivada (reader MDB_ADO_1) [off]
    attributes: OBJECTID autonumber, SHAPE oleobject, simbolizarCartaMini integer, geometriaAproximada long, tipoLavoura long, nomeAbrev text(255), fkClassificador text(255), obsAquisicao text(255), denso long, espessuraDAP single, classificacaoPorte long, controleId text(255), cultivoPredominante long, alturaMediaIndividuos single, terreno long, espacamentoIndividuos single, finalidade long, nome text(255), controle_id text(200), SHAPE_Length double, SHAPE_Area double
    -> AttributeFilter
GDB_DatabaseLocks (reader MDB_ADO_1) [off]
    attributes: LockID autonumber, LockType long, UserName memo, MachineName memo
    -> AttributeFilter
Edif_Ensino_point (reader MDB_ADO_1) [off]
    attributes: OBJECTID autonumber, SHAPE oleobject, geometriaAproximada long, offSetSimbX single, orientacao single, tipoClasseCnae long, fkComplOrgEnsino text(255), nome text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Cidade_SHAPE_Index (reader MDB_ADO_1) [off]
    attributes: IndexedObjectId long, MinGX long, MinGY long, MaxGX long, MaxGY long
    -> AttributeFilter
Identific_Trecho_Rod_SHAPE_Index (reader MDB_ADO_1) [off]
    attributes: IndexedObjectId long, MinGX long, MinGY long, MaxGX long, MaxGY long
    -> AttributeFilter
Pista_Competicao_line_SHAPE_Index (reader MDB_ADO_1) [off]
    attributes: IndexedObjectId long, MinGX long, MinGY long, MaxGX long, MaxGY long
    -> AttributeFilter
Edif_Const_Lazer_polygon_SHAPE_Index (reader MDB_ADO_1) [off]
    attributes: IndexedObjectId long, MinGX long, MinGY long, MaxGX long, MaxGY long
    -> AttributeFilter
Edif_Const_Lazer_point (reader MDB_ADO_1) [off]
    attributes: OBJECTID autonumber, SHAPE oleobject, geometriaAproximada long, offSetSimbX single, orientacao single, nome text(255), tipoEdifLazer long, fkComplLazer text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
GDB_GeomColumns (reader MDB_ADO_1) [off]
    attributes: TableName text(255), FieldName text(255), ShapeType long, ExtentLeft double, ExtentBottom double, ExtentRight double, ExtentTop double, IdxOriginX double, IdxOriginY double, IdxGridSize double, SRID long, HasZ yesno, HasM yesno, ZLow double, ZHigh double, MLow double, MHigh double
    -> AttributeFilter
Patio_polygon_SHAPE_Index (reader MDB_ADO_1) [off]
    attributes: IndexedObjectId long, MinGX long, MinGY long, MaxGX long, MaxGY long
    -> AttributeFilter
Trecho_Duto_SHAPE_Index (reader MDB_ADO_1) [off]
    attributes: IndexedObjectId long, MinGX long, MinGY long, MaxGX long, MaxGY long
    -> AttributeFilter
T_1_PolyErrors_Shape_Index (reader MDB_ADO_1) [off]
    attributes: IndexedObjectId long, MinGX long, MinGY long, MaxGX long, MaxGY long
    -> AttributeFilter
Comporta_line (reader MDB_ADO_1) [off]
    attributes: OBJECTID autonumber, SHAPE oleobject, offSetX single, orientacao single, justTxt long, situacaoFisica long, nomeAbrev text(255), simbolizarCartaMini integer, controleId text(255), nome text(255), operacional long, obsAquisicao text(255), fkClassificador text(255), offSetY single, geometriaAproximada long, controle_id text(200), SHAPE_Length double
    -> AttributeFilter
Elemento_Fisiog_Natural_point (reader MDB_ADO_1) [off]
    attributes: OBJECTID autonumber, SHAPE oleobject, controleId text(255), tamanhoTxt single, justTxt long, tipoElemNat long, offSetY single, nomeAbrev text(255), geometriaAproximada long, simbolizarCartaMini integer, nome text(255), offSetX single, obsAquisicao text(255), fkClassificador text(255), controle_id text(200)
    -> AttributeFilter
Edif_Ext_Mineral_point (reader MDB_ADO_1) [off]
    attributes: OBJECTID autonumber, SHAPE oleobject, geometriaAproximada long, offSetSimbX single, orientacao single, fkComplOrgExtMin text(255), nome text(255), offSetY single, justTxt long, offSetX single, offSetSimbY single, nomeAbrev text(255), matConstr long, operacional long, simbolizarCartaMini integer, tipoDivisaoCnae long, obsAquisicao text(255), controleId text(255), situacaoFisica long, escalaMaxSimbolizar long, fkClassificador text(255), controle_id text(200)
    -> AttributeFilter
Massa_Dagua (reader MDB_ADO_1) [off]
    attributes: OBJECTID autonumber, SHAPE oleobject, controleId text(255), salinidade long, regime long, geometriaAproximada long, simbolizarCartaMini integer, fkClassificador text(255), obsAquisicao text(255), nomeAbrev text(255), tipoMassaDagua long, nome text(255), controle_id text(200), SHAPE_Length double, SHAPE_Area double
    -> AttributeFilter
Trecho_Massa_Dagua (reader MDB_ADO_1) [off]
    attributes: OBJECTID autonumber, SHAPE oleobject, controleId text(255), salinidade long, regime long, geometriaAproximada long, simbolizarCartaMini integer, fkClassificador text(255), obsAquisicao text(255), fkComplTrCurDagua text(255), nomeAbrev text(255), tipoMassaDagua long, nome text(255), controle_id text(200), SHAPE_Length double, SHAPE_Area double
    -> AttributeFilter
GDB_ItemRelationshipTypes (reader MDB_ADO_1) [off]
    attributes: ObjectID autonumber, UUID replicationid, OrigItemTypeID replicationid, DestItemTypeID replicationid, Name text(160), ForwardLabel text(255), BackwardLabel text(255), IsContainment integer
    -> AttributeFilter
T_1_DirtyAreas_DirtyArea_Index (reader MDB_ADO_1) [off]
    attributes: IndexedObjectId long, MinGX long, MinGY long, MaxGX long, MaxGY long
    -> AttributeFilter
Dep_Abast_Agua_point_SHAPE_Index (reader MDB_ADO_1) [off]
    attributes: IndexedObjectId long, MinGX long, MinGY long, MaxGX long, MaxGY long
    -> AttributeFilter
Ponto_Trecho_Energia (reader MDB_ADO_1) [off]
    attributes: OBJECTID autonumber, SHAPE oleobject, obsAquisicao text(255), fkClassificador text(255), simbolizarCartaMini integer, geometriaAproximada long, controleId text(255), tipoPtoEnergia long, controle_id text(200)
    -> AttributeFilter
Cerrado_Cerradao (reader MDB_ADO_1) [off]
    attributes: OBJECTID autonumber, SHAPE oleobject, alturaMediaIndividuos single, nomeAbrev text(255), controleId text(255), denso long, obsAquisicao text(255), simbolizarCartaMini integer, classificacaoPorte long, antropizada long, tipoCerr long, nome text(255), geometriaAproximada long, fkClassificador text(255), controle_id text(200), SHAPE_Length double, SHAPE_Area double
    -> AttributeFilter
Curva_Nivel (reader MDB_ADO_1) [off]
    attributes: OBJECTID autonumber, SHAPE oleobject, indice long, depressao long, controleId text(255), obsAquisicao text(255), cota long, simbolizarCartaMini integer, escalaMaxSimbolizar long, ordemTickDepressao long, geometriaAproximada long, fkClassificador text(255), emMassaDagua long, cotadaPorProcesso long, controle_id text(200), SHAPE_Length double
    -> AttributeFilter
Edif_Saneamento_point (reader MDB_ADO_1) [off]
    attributes: OBJECTID autonumber, SHAPE oleobject, fkComplSaneam text(255), geometriaAproximada long, offSetSimbX single, orientacao single, nome text(255), offSetY single, justTxt long, offSetX single, offSetSimbY single, nomeAbrev text(255), tipoEdifSaneam long, matConstr long, operacional long, simbolizarCartaMini integer, obsAquisicao text(255), controleId text(255), situacaoFisica long, escalaMaxSimbolizar long, fkClassificador text(255), controle_id text(200)
    -> AttributeFilter
Patio_polygon (reader MDB_ADO_1) [off]
    attributes: OBJECTID autonumber, SHAPE oleobject, fkComplAeroport text(255), nomeAbrev text(255), fkComplPortuario text(255), fkComplOrgRel text(255), fkClassificador text(255), situacaoFisica long, fkComplIndustria text(255), simbolizarCartaMini integer, obsAquisicao text(255), nome text(255), fkComplOrgEnsino text(255), operacional long, administracao long, fkComplOrgComSv text(255), escalaMaxSimbolizar long, controleId text(255), offSetSimbY single, offSetY single, geometriaAproximada long, orientacao single, fkComplOrgExtMin text(255), modalUso long, justTxt long, offSetX single, offSetSimbX single, fkComplLazer text(255), fkComplOrgAgrop text(255), fkComplEstrApoio text(255),
      controle_id text(200), SHAPE_Length double, SHAPE_Area double
    -> AttributeFilter
Entroncamento (reader MDB_ADO_1) [off]
    attributes: OBJECTID autonumber, SHAPE oleobject, controleId text(255), justTxt long, geometriaAproximada long, simbolizarCartaMini integer, fkClassificador text(255), obsAquisicao text(255), nomeAbrev text(255), tipoEntroncamento long, offSetY single, offSetX single, nome text(255), controle_id text(200)
    -> AttributeFilter
Dep_Saneamento_point (reader MDB_ADO_1) [off]
    attributes: OBJECTID autonumber, SHAPE oleobject, fkComplSaneam text(255), geometriaAproximada long, fkClassificador text(255), offSetSimbX single, residuo long, orientacao single, nome text(255), offSetY single, justTxt long, offSetX single, offSetSimbY single, nomeAbrev text(255), finalidade long, construcao long, matConstr long, operacional long, simbolizarCartaMini integer, obsAquisicao text(255), controleId text(255), tipoDepSaneam long, situacaoFisica long, escalaMaxSimbolizar long, tipoResiduo long, controle_id text(200)
    -> AttributeFilter
Edif_Comerc_Serv_point (reader MDB_ADO_1) [off]
    attributes: OBJECTID autonumber, SHAPE oleobject, geometriaAproximada long, fkComplOrgComSv text(255), offSetSimbX single, orientacao single, nome text(255), offSetY single, justTxt long, offSetX single, offSetSimbY single, nomeAbrev text(255), finalidade long, matConstr long, tipoEdifComercServ long, operacional long, simbolizarCartaMini integer, obsAquisicao text(255), controleId text(255), situacaoFisica long, escalaMaxSimbolizar long, fkClassificador text(255), controle_id text(200)
    -> AttributeFilter
Selections (reader MDB_ADO_1) [off]
    attributes: SelectionID autonumber, TargetName text(255)
    -> AttributeFilter
Nome_Local_SHAPE_Index (reader MDB_ADO_1) [off]
    attributes: IndexedObjectId long, MinGX long, MinGY long, MaxGX long, MaxGY long
    -> AttributeFilter
Edif_Pub_Civil_point (reader MDB_ADO_1) [off]
    attributes: OBJECTID autonumber, SHAPE oleobject, geometriaAproximada long, offSetSimbX single, orientacao single, fkComplPubCivil text(255), tipoEdif long, nome text(255), offSetY single, justTxt long, tipoUsoEdif long, offSetX single, offSetSimbY single, nomeAbrev text(255), matConstr long, operacional long, simbolizarCartaMini integer, obsAquisicao text(255), controleId text(255), situacaoFisica long, escalaMaxSimbolizar long, fkClassificador text(255), controle_id text(200)
    -> AttributeFilter
GDB_Items (reader MDB_ADO_1) [off]
    attributes: ObjectID autonumber, UUID replicationid, Type replicationid, Name text(160), PhysicalName text(160), Path memo, DatasetSubtype1 long, DatasetSubtype2 long, DatasetInfo1 text(255), DatasetInfo2 text(255), URL text(255), Definition memo, Documentation memo, ItemInfo memo, Properties long, Defaults oleobject, Shape oleobject
    -> AttributeFilter
Atracadouro_point_SHAPE_Index (reader MDB_ADO_1) [off]
    attributes: IndexedObjectId long, MinGX long, MinGY long, MaxGX long, MaxGY long
    -> AttributeFilter
Edif_Constr_Est_Med_point (reader MDB_ADO_1) [off]
    attributes: OBJECTID autonumber, SHAPE oleobject, geometriaAproximada long, offSetSimbX single, orientacao single, fkComplEstMedFen text(255), nome text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Campo_Quadra_polygon (reader MDB_ADO_1) [off]
    attributes: OBJECTID autonumber, SHAPE oleobject, fkClassificador text(255), geometriaAproximada long, offSetSimbX single, orientacao single, nome text(255), fkComplLazer text(255), offSetY single, justTxt long, offSetX single, offSetSimbY single, nomeAbrev text(255), operacional long, simbolizarCartaMini integer, obsAquisicao text(255), controleId text(255), situacaoFisica long, escalaMaxSimbolizar long, tipoCampoQuadra long, controle_id text(200), SHAPE_Length double, SHAPE_Area double
    -> AttributeFilter
Posto_Combustivel_point_SHAPE_Index (reader MDB_ADO_1) [off]
    attributes: IndexedObjectId long, MinGX long, MinGY long, MaxGX long, MaxGY long
    -> AttributeFilter
Edif_Comerc_Serv_polygon (reader MDB_ADO_1) [off]
    attributes: OBJECTID autonumber, SHAPE oleobject, geometriaAproximada long, fkComplOrgComSv text(255), offSetSimbX single, orientacao single, nome text(255), offSetY single, justTxt long, offSetX single, offSetSimbY single, nomeAbrev text(255), finalidade long, matConstr long, tipoEdifComercServ long, operacional long, simbolizarCartaMini integer, obsAquisicao text(255), controleId text(255), situacaoFisica long, escalaMaxSimbolizar long, fkClassificador text(255), controle_id text(200), SHAPE_Length double, SHAPE_Area double
    -> AttributeFilter
Edif_Rodoviaria_point_SHAPE_Index (reader MDB_ADO_1) [off]
    attributes: IndexedObjectId long, MinGX long, MinGY long, MaxGX long, MaxGY long
    -> AttributeFilter
Ponte_point (reader MDB_ADO_1) [off]
    attributes: OBJECTID autonumber, SHAPE oleobject, nomeAbrev text(255), largura single, extensao single, vaoVertical single, vaoLivreHoriz single, situacaoFisica long, simbolizarCartaMini integer, nrFaixas long, obsAquisicao text(255), nome text(255), tipoPonte long, nrPistas long, operacional long, matConstr long, escalaMaxSimbolizar long, controleId text(255), offSetSimbY single, offSetY single, necessidadeManutencao long, geometriaAproximada long, orientacao single, modalUso long, justTxt long, fkClassificador text(255), pesoMaxSuportTon single, offSetX single, offSetSimbX single, posicaoPista long,
      controle_id text(200)
    -> AttributeFilter
Trilha_Picada (reader MDB_ADO_1) [off]
    attributes: OBJECTID autonumber, SHAPE oleobject, fkClassificador text(255), obsAquisicao text(255), controleId text(255), geometriaAproximada long, simbolizarCartaMini integer, escalaMaxSimbolizar long, nomeAbrev text(255), nome text(255), controle_id text(200), SHAPE_Length double
    -> AttributeFilter
Edif_Const_Aeroportuaria_point (reader MDB_ADO_1) [off]
    attributes: OBJECTID autonumber, SHAPE oleobject, geometriaAproximada long, offSetSimbX single, orientacao single, fkComplAeroport text(255), tipoEdifAero long, nome text(255), offSetY single, justTxt long, offSetX single, offSetSimbY single, nomeAbrev text(255), administracao long, matConstr long, operacional long, simbolizarCartaMini integer, obsAquisicao text(255), controleId text(255), situacaoFisica long, escalaMaxSimbolizar long, fkClassificador text(255), controle_id text(200)
    -> AttributeFilter
Area_Industrial (reader MDB_ADO_1) [off]
    attributes: OBJECTID autonumber, SHAPE oleobject, fkClassificador text(255), obsAquisicao text(255), controleId text(255), geometriaAproximada long, simbolizarCartaMini integer, fkComplIndustria text(255), escalaMaxSimbolizar long, controle_id text(200), SHAPE_Length double, SHAPE_Area double
    -> AttributeFilter
Edif_Religiosa_polygon_SHAPE_Index (reader MDB_ADO_1) [off]
    attributes: IndexedObjectId long, MinGX long, MinGY long, MaxGX long, MaxGY long
    -> AttributeFilter
Deposito_Geral_point_SHAPE_Index (reader MDB_ADO_1) [off]
    attributes: IndexedObjectId long, MinGX long, MinGY long, MaxGX long, MaxGY long
    -> AttributeFilter
Torre_Comunic_SHAPE_Index (reader MDB_ADO_1) [off]
    attributes: IndexedObjectId long, MinGX long, MinGY long, MaxGX long, MaxGY long
    -> AttributeFilter
Limite_Massa_Dagua (reader MDB_ADO_1) [off]
    attributes: OBJECTID autonumber, SHAPE oleobject, materialPredominante long, controleId text(255), geometriaAproximada long, simbolizarCartaMini integer, fkClassificador text(255), obsAquisicao text(255), nomeAbrev text(255), tipoLimMassa long, alturaMediaMargem single, nome text(255), controle_id text(200), SHAPE_Length double
    -> AttributeFilter
Edif_Rodoviaria_polygon_SHAPE_Index (reader MDB_ADO_1) [off]
    attributes: IndexedObjectId long, MinGX long, MinGY long, MaxGX long, MaxGY long
    -> AttributeFilter
Sumidouro_Vertedouro (reader MDB_ADO_1) [off]
    attributes: OBJECTID autonumber, SHAPE oleobject, orientacao single, nomeAbrev text(255), controleId text(255), tipoSumVert long, obsAquisicao text(255), simbolizarCartaMini integer, justTxt long, nome text(255), offSetX single, geometriaAproximada long, fkClassificador text(255), offSetY single, causa long, controle_id text(200)
    -> AttributeFilter
Edif_Pub_Militar_point (reader MDB_ADO_1) [off]
    attributes: OBJECTID autonumber, SHAPE oleobject, geometriaAproximada long, fkComplMilitar text(255), offSetSimbX single, orientacao single, tipoEdif long, nome text(255), offSetY single, justTxt long, tipoUsoEdif long, offSetX single, offSetSimbY single, nomeAbrev text(255), matConstr long, operacional long, simbolizarCartaMini integer, obsAquisicao text(255), controleId text(255), situacaoFisica long, escalaMaxSimbolizar long, fkClassificador text(255), controle_id text(200)
    -> AttributeFilter
Ilha_polygon (reader MDB_ADO_1) [off]
    attributes: OBJECTID autonumber, SHAPE oleobject, controleId text(255), tamanhoTxt single, justTxt long, tipoElemNat long, offSetY single, nomeAbrev text(255), geometriaAproximada long, simbolizarCartaMini integer, nome text(255), offSetX single, obsAquisicao text(255), fkClassificador text(255), controle_id text(200), SHAPE_Length double, SHAPE_Area double
    -> AttributeFilter
GDB_ReplicaLog (reader MDB_ADO_1) [off]
    attributes: ID autonumber, ReplicaID long, Event long, ErrorCode long, LogDate datetime, SourceBeginGen long, SourceEndGen long, TargetGen long
    -> AttributeFilter
Galeria_Bueiro_point (reader MDB_ADO_1) [off]
    attributes: OBJECTID autonumber, SHAPE oleobject, geometriaAproximada long, offSetSimbX single, orientacao single, nome text(255), offSetY single, justTxt long, offSetX single, offSetSimbY single, nomeAbrev text(255), matConstr long, operacional long, simbolizarCartaMini integer, obsAquisicao text(255), controleId text(255), pesoMaxSuportTon single, situacaoFisica long, escalaMaxSimbolizar long, fkClassificador text(255), controle_id text(200)
    -> AttributeFilter
Deposito_Geral_point (reader MDB_ADO_1) [off]
    attributes: OBJECTID autonumber, SHAPE oleobject, nome text(255), tipoExposicao long, fkComplOrgExtMin text(255), fkComplAeroport text(255), simbolizarCartaMini integer, tipoProdutoResiduo long, tipoConteudo long, valorVolume single, fkComplOrgComSv text(255), tratamento long, nomeAbrev text(255), fkComplIndustria text(255), offSetY single, operacional long, offSetSimbX single, situacaoFisica long, geometriaAproximada long, fkComplPortuario text(255), fkClassificador text(255), obsAquisicao text(255), offSetSimbY single, justTxt long, fkComplGerEnEletr text(255), fkComplOrgAgrop text(255), orientacao single, matConstr long, tipoDepGeral long, offSetX single,
      fkComplEstrApoio text(255), unidadeVolume long, controleId text(255), escalaMaxSimbolizar long, controle_id text(200)
    -> AttributeFilter
Edif_Ensino_polygon_SHAPE_Index (reader MDB_ADO_1) [off]
    attributes: IndexedObjectId long, MinGX long, MinGY long, MaxGX long, MaxGY long
    -> AttributeFilter
Edif_Comerc_Serv_point_SHAPE_Index (reader MDB_ADO_1) [off]
    attributes: IndexedObjectId long, MinGX long, MinGY long, MaxGX long, MaxGY long
    -> AttributeFilter
Edif_Ext_Mineral_polygon (reader MDB_ADO_1) [off]
    attributes: OBJECTID autonumber, SHAPE oleobject, geometriaAproximada long, offSetSimbX single, orientacao single, fkComplOrgExtMin text(255), nome text(255), offSetY single, justTxt long, offSetX single, offSetSimbY single, nomeAbrev text(255), matConstr long, operacional long, simbolizarCartaMini integer, tipoDivisaoCnae long, obsAquisicao text(255), controleId text(255), situacaoFisica long, escalaMaxSimbolizar long, fkClassificador text(255), controle_id text(200), SHAPE_Length double, SHAPE_Area double
    -> AttributeFilter
Alter_Fisiog_Antropica_line_SHAPE_Index (reader MDB_ADO_1) [off]
    attributes: IndexedObjectId long, MinGX long, MinGY long, MaxGX long, MaxGY long
    -> AttributeFilter
T_1_LineErrors (reader MDB_ADO_1) [off]
    attributes: ObjectID autonumber, OriginClassID long, OriginID long, DestClassID long, DestID long, TopoRuleType long, TopoRuleID long, Shape oleobject, IsException long, Shape_Length double
    -> AttributeFilter
Campo_Quadra_point (reader MDB_ADO_1) [off]
    attributes: OBJECTID autonumber, SHAPE oleobject, fkClassificador text(255), geometriaAproximada long, offSetSimbX single, orientacao single, nome text(255), fkComplLazer text(255), offSetY single, justTxt long, offSetX single, offSetSimbY single, nomeAbrev text(255), operacional long, simbolizarCartaMini integer, obsAquisicao text(255), controleId text(255), situacaoFisica long, escalaMaxSimbolizar long, tipoCampoQuadra long, controle_id text(200)
    -> AttributeFilter
Edif_Industrial_polygon (reader MDB_ADO_1) [off]
    attributes: OBJECTID autonumber, SHAPE oleobject, geometriaAproximada long, offSetSimbX single, orientacao single, nome text(255), offSetY single, justTxt long, fkComplIndustria text(255), offSetX single, offSetSimbY single, chamine long, nomeAbrev text(255), matConstr long, operacional long, simbolizarCartaMini integer, tipoDivisaoCnae long, obsAquisicao text(255), controleId text(255), situacaoFisica long, escalaMaxSimbolizar long, fkClassificador text(255), controle_id text(200), SHAPE_Length double, SHAPE_Area double
    -> AttributeFilter
Pto_Est_Med_Fenomenos (reader MDB_ADO_1) [off]
    attributes: OBJECTID autonumber, SHAPE oleobject, geometriaAproximada long, codEstacao text(255), offSetSimbX single, fkComplEstMedFen text(255), orgaoEnteResp text(255), nome text(255), tipoPtoEstMed long, offSetY single, justTxt long, offSetX single, offSetSimbY single, nomeAbrev text(255), simbolizarCartaMini integer, obsAquisicao text(255), controleId text(255), escalaMaxSimbolizar long, fkClassificador text(255), controle_id text(200)
    -> AttributeFilter
Gruta_Caverna_point_SHAPE_Index (reader MDB_ADO_1) [off]
    attributes: IndexedObjectId long, MinGX long, MinGY long, MaxGX long, MaxGY long
    -> AttributeFilter
Pista_Competicao_line (reader MDB_ADO_1) [off]
    attributes: OBJECTID autonumber, SHAPE oleobject, geometriaAproximada long, orientacao single, tipoPista long, nome text(255), fkComplLazer text(255), offSetY single, justTxt long, offSetX single, nomeAbrev text(255), operacional long, simbolizarCartaMini integer, obsAquisicao text(255), controleId text(255), situacaoFisica long, escalaMaxSimbolizar long, fkClassificador text(255), controle_id text(200), SHAPE_Length double
    -> AttributeFilter
Edif_Habitacional_point_SHAPE_Index (reader MDB_ADO_1) [off]
    attributes: IndexedObjectId long, MinGX long, MinGY long, MaxGX long, MaxGY long
    -> AttributeFilter
Edif_Abast_Agua_point_SHAPE_Index (reader MDB_ADO_1) [off]
    attributes: IndexedObjectId long, MinGX long, MinGY long, MaxGX long, MaxGY long
    -> AttributeFilter
Nome_Local (reader MDB_ADO_1) [off]
    attributes: OBJECTID autonumber, SHAPE oleobject, nomeAbrev text(255), controleId text(255), obsAquisicao text(255), simbolizarCartaMini integer, justTxt long, escalaMaxSimbolizar long, nome text(255), tamanhoTxt single, offSetX single, geometriaAproximada long, fkClassificador text(255), offSetY single, controle_id text(200)
    -> AttributeFilter
Delimitacao_Fisica_SHAPE_Index (reader MDB_ADO_1) [off]
    attributes: IndexedObjectId long, MinGX long, MinGY long, MaxGX long, MaxGY long
    -> AttributeFilter
Edif_Ext_Mineral_point_SHAPE_Index (reader MDB_ADO_1) [off]
    attributes: IndexedObjectId long, MinGX long, MinGY long, MaxGX long, MaxGY long
    -> AttributeFilter
Limite_Massa_Dagua_SHAPE_Index (reader MDB_ADO_1) [off]
    attributes: IndexedObjectId long, MinGX long, MinGY long, MaxGX long, MaxGY long
    -> AttributeFilter
Ponto_Rodoviario_Ferrov_SHAPE_Index (reader MDB_ADO_1) [off]
    attributes: IndexedObjectId long, MinGX long, MinGY long, MaxGX long, MaxGY long
    -> AttributeFilter
Confluencia (reader MDB_ADO_1) [off]
    attributes: OBJECTID autonumber, SHAPE oleobject, controleId text(255), justTxt long, geometriaAproximada long, simbolizarCartaMini integer, fkClassificador text(255), obsAquisicao text(255), nomeAbrev text(255), offSetY single, offSetX single, relacionado long, nome text(255), controle_id text(200)
    -> AttributeFilter
Posto_Combustivel_point (reader MDB_ADO_1) [off]
    attributes: OBJECTID autonumber, SHAPE oleobject, geometriaAproximada long, offSetSimbX single, orientacao single, nome text(255), offSetY single, justTxt long, offSetX single, offSetSimbY single, nomeAbrev text(255), administracao long, matConstr long, operacional long, simbolizarCartaMini integer, fkComplEstrApoio text(255), obsAquisicao text(255), controleId text(255), situacaoFisica long, escalaMaxSimbolizar long, fkClassificador text(255), controle_id text(200)
    -> AttributeFilter
Edif_Comunic_point_SHAPE_Index (reader MDB_ADO_1) [off]
    attributes: IndexedObjectId long, MinGX long, MinGY long, MaxGX long, MaxGY long
    -> AttributeFilter
Edif_Comunic_point (reader MDB_ADO_1) [off]
    attributes: OBJECTID autonumber, SHAPE oleobject, geometriaAproximada long, offSetSimbX single, orientacao single, tipoEdifComunic long, nome text(255), modalidade long, fkComplComunic text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
GDB_ItemRelationships (reader MDB_ADO_1) [off]
    attributes: ObjectID autonumber, UUID replicationid, OriginID replicationid, DestID replicationid, Type replicationid, Attributes memo, Properties long
    -> AttributeFilter
Gruta_Caverna_point (reader MDB_ADO_1) [off]
    attributes: OBJECTID autonumber, SHAPE oleobject, offSetX single, orientacao single, tipoElemNat long, justTxt long, nomeAbrev text(255), simbolizarCartaMini integer, controleId text(255), nome text(255), obsAquisicao text(255), fkClassificador text(255), offSetY single, tamanhoTxt single, geometriaAproximada long, controle_id text(200)
    -> AttributeFilter
Area_Energia_Eletrica (reader MDB_ADO_1) [off]
    attributes: OBJECTID autonumber, SHAPE oleobject, fkClassificador text(255), obsAquisicao text(255), controleId text(255), geometriaAproximada long, simbolizarCartaMini integer, fkComplGerEnEletr text(255), fkComplSubEnEletr text(255), escalaMaxSimbolizar long, controle_id text(200), SHAPE_Length double, SHAPE_Area double
    -> AttributeFilter
Edif_Religiosa_polygon (reader MDB_ADO_1) [off]
    attributes: OBJECTID autonumber, SHAPE oleobject, geometriaAproximada long, offSetSimbX single, orientacao single, religiao text(255), nome text(255), fkComplOrgRel text(255), offSetY single, justTxt long, offSetX single, offSetSimbY single, nomeAbrev text(255), matConstr long, operacional long, tipoEdifRelig long, simbolizarCartaMini integer, ensino long, obsAquisicao text(255), controleId text(255), situacaoFisica long, escalaMaxSimbolizar long, fkClassificador text(255), controle_id text(200), SHAPE_Length double, SHAPE_Area double
    -> AttributeFilter
Edif_Industrial_polygon_SHAPE_Index (reader MDB_ADO_1) [off]
    attributes: IndexedObjectId long, MinGX long, MinGY long, MaxGX long, MaxGY long
    -> AttributeFilter
Edif_Abast_Agua_point (reader MDB_ADO_1) [off]
    attributes: OBJECTID autonumber, SHAPE oleobject, geometriaAproximada long, offSetSimbX single, tipoEdifAbast long, orientacao single, nome text(255), offSetY single, justTxt long, offSetX single, offSetSimbY single, nomeAbrev text(255), matConstr long, operacional long, simbolizarCartaMini integer, fkComplAbsAgua text(255), obsAquisicao text(255), controleId text(255), situacaoFisica long, escalaMaxSimbolizar long, fkClassificador text(255), controle_id text(200)
    -> AttributeFilter
Dep_Saneamento_polygon_SHAPE_Index (reader MDB_ADO_1) [off]
    attributes: IndexedObjectId long, MinGX long, MinGY long, MaxGX long, MaxGY long
    -> AttributeFilter
Area_Uso_Comunitario_point_SHAPE_Index (reader MDB_ADO_1) [off]
    attributes: IndexedObjectId long, MinGX long, MinGY long, MaxGX long, MaxGY long
    -> AttributeFilter
Edif_Saude_point (reader MDB_ADO_1) [off]
    attributes: OBJECTID autonumber, SHAPE oleobject, geometriaAproximada long, fkComplSaude text(255), offSetSimbX single, orientacao single, tipoClasseCnae long, nome text(255), nivelAtencao long, offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Area_Industrial_SHAPE_Index (reader MDB_ADO_1) [off]
    attributes: IndexedObjectId long, MinGX long, MinGY long, MaxGX long, MaxGY long
    -> AttributeFilter
Edif_Saude_polygon (reader MDB_ADO_1) [off]
    attributes: OBJECTID autonumber, SHAPE oleobject, geometriaAproximada long, fkComplSaude text(255), offSetSimbX single, orientacao single, tipoClasseCnae long, nome text(255), nivelAtencao long, offSetY single, justTxt long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
Est_Gerad_Energia_Eletr_polygon_SHAPE_Index (reader MDB_ADO_1) [off]
    attributes: IndexedObjectId long, MinGX long, MinGY long, MaxGX long, MaxGY long
    -> AttributeFilter
Area_Lazer (reader MDB_ADO_1) [off]
    attributes: OBJECTID autonumber, SHAPE oleobject, fkClassificador text(255), obsAquisicao text(255), fkComplLazer text(255), geometriaAproximada long, simbolizarCartaMini integer, controleId text(255), escalaMaxSimbolizar long, controle_id text(200), SHAPE_Length double, SHAPE_Area double
    -> AttributeFilter
Atracadouro_point (reader MDB_ADO_1) [off]
    attributes: OBJECTID autonumber, SHAPE oleobject, geometriaAproximada long, offSetSimbX single, orientacao single, fkComplPortuario text(255), nome text(255), offSetY single, justTxt long, offSetX single, offSetSimbY single, nomeAbrev text(255), administracao long, matConstr long, operacional long, simbolizarCartaMini integer, tipoAtracad long, obsAquisicao text(255), controleId text(255), situacaoFisica long, escalaMaxSimbolizar long, fkClassificador text(255), controle_id text(200)
    -> AttributeFilter
Trecho_Duto (reader MDB_ADO_1) [off]
    attributes: OBJECTID autonumber, SHAPE oleobject, tipoTrechoDuto long, geometriaAproximada long, setor long, nome text(255), posicaoRelativa long, situacaoEspacial long, nomeAbrev text(255), matConstr long, operacional long, simbolizarCartaMini integer, fkComplDuto text(255), obsAquisicao text(255), controleId text(255), nrDutos long, matTransp long, situacaoFisica long, fkClassificador text(255), controle_id text(200), SHAPE_Length double
    -> AttributeFilter
Ponte_point_SHAPE_Index (reader MDB_ADO_1) [off]
    attributes: IndexedObjectId long, MinGX long, MinGY long, MaxGX long, MaxGY long
    -> AttributeFilter
Antena_Comunic_SHAPE_Index (reader MDB_ADO_1) [off]
    attributes: IndexedObjectId long, MinGX long, MinGY long, MaxGX long, MaxGY long
    -> AttributeFilter
Edif_Agrop_Ext_Veg_Pesca_point (reader MDB_ADO_1) [off]
    attributes: OBJECTID autonumber, SHAPE oleobject, geometriaAproximada long, offSetSimbX single, orientacao single, nome text(255), offSetY single, justTxt long, offSetX single, offSetSimbY single, nomeAbrev text(255), matConstr long, fkComplOrgAgrop text(255), operacional long, tipoEdifAgropec long, simbolizarCartaMini integer, tamanhoTxt single, obsAquisicao text(255), controleId text(255), situacaoFisica long, escalaMaxSimbolizar long, fkClassificador text(255), controle_id text(200)
    -> AttributeFilter
Area_Ext_Mineral (reader MDB_ADO_1) [off]
    attributes: OBJECTID autonumber, SHAPE oleobject, fkClassificador text(255), obsAquisicao text(255), geometriaAproximada long, simbolizarCartaMini integer, controleId text(255), escalaMaxSimbolizar long, fkComplOrgExtMin text(255), controle_id text(200), SHAPE_Length double, SHAPE_Area double
    -> AttributeFilter
Massa_Dagua_SHAPE_Index (reader MDB_ADO_1) [off]
    attributes: IndexedObjectId long, MinGX long, MinGY long, MaxGX long, MaxGY long
    -> AttributeFilter
Aglomerado_Rural (reader MDB_ADO_1) [off]
    attributes: OBJECTID autonumber, SHAPE oleobject, tipoAglomerado long, geometriaAproximada long, offSetSimbX single, identificadorPosicGeo text(255), orientacao single, nome text(255), simbolizar integer, offSetY single, justTxt long, longitude single, offSetX single, offSetSimbY single, latitude single, nomeAbrev text(255), longitude_txt text(255), simbolizarCartaMini integer, tamanhoTxt single, latitude_txt text(255), obsAquisicao text(255), controleId text(255), fkClassificador text(255), controle_id text(200)
    -> AttributeFilter
Elemento_Fisiog_Natural_line (reader MDB_ADO_1) [off]
    attributes: OBJECTID autonumber, SHAPE oleobject, controleId text(255), tamanhoTxt single, justTxt long, tipoElemNat long, offSetY single, nomeAbrev text(255), geometriaAproximada long, simbolizarCartaMini integer, nome text(255), offSetX single, obsAquisicao text(255), fkClassificador text(255), controle_id text(200), SHAPE_Length double
    -> AttributeFilter
Pista_Ponto_Pouso_polygon (reader MDB_ADO_1) [off]
    attributes: OBJECTID autonumber, SHAPE oleobject, geometriaAproximada long, revestimento long, homologacao long, orientacao single, tipoPista long, fkComplAeroport text(255), nome text(255), largura single, usoPista long, offSetY single, justTxt long, offSetX single, nomeAbrev text(255), operacional long, simbolizarCartaMini integer, extensao single, obsAquisicao text(255), controleId text(255), situacaoFisica long, fkClassificador text(255), controle_id text(200), SHAPE_Length double, SHAPE_Area double
    -> AttributeFilter
Fonte_Dagua (reader MDB_ADO_1) [off]
    attributes: OBJECTID autonumber, SHAPE oleobject, geometriaAproximada long, offSetSimbX single, tipoFonteDagua long, orientacao single, nome text(255), offSetY single, justTxt long, offSetX single, offSetSimbY single, nomeAbrev text(255), regime long, simbolizarCartaMini integer, qualidAgua long, obsAquisicao text(255), controleId text(255), escalaMaxSimbolizar long, fkClassificador text(255), controle_id text(200)
    -> AttributeFilter
Curva_Nivel_SHAPE_Index (reader MDB_ADO_1) [off]
    attributes: IndexedObjectId long, MinGX long, MinGY long, MaxGX long, MaxGY long
    -> AttributeFilter
Dep_Saneamento_point_SHAPE_Index (reader MDB_ADO_1) [off]
    attributes: IndexedObjectId long, MinGX long, MinGY long, MaxGX long, MaxGY long
    -> AttributeFilter
SelectedObjects (reader MDB_ADO_1) [off]
    attributes: SelectionID long, ObjectID long
    -> AttributeFilter
Area_Edificada_SHAPE_Index (reader MDB_ADO_1) [off]
    attributes: IndexedObjectId long, MinGX long, MinGY long, MaxGX long, MaxGY long
    -> AttributeFilter
Terreno_Suj_Inundacao (reader MDB_ADO_1) [off]
    attributes: OBJECTID autonumber, SHAPE oleobject, fkClassificador text(255), obsAquisicao text(255), controleId text(255), geometriaAproximada long, periodicidadeInunda text(255), simbolizarCartaMini integer, nomeAbrev text(255), nome text(255), controle_id text(200), SHAPE_Length double, SHAPE_Area double
    -> AttributeFilter
Edif_Rodoviaria_point (reader MDB_ADO_1) [off]
    attributes: OBJECTID autonumber, SHAPE oleobject, geometriaAproximada long, offSetSimbX single, orientacao single, nome text(255), offSetY single, justTxt long, offSetX single, offSetSimbY single, tipoEdifRod long, administracao long, nomeAbrev text(255), matConstr long, operacional long, simbolizarCartaMini integer, fkComplEstrApoio text(255), obsAquisicao text(255), controleId text(255), situacaoFisica long, escalaMaxSimbolizar long, fkClassificador text(255), controle_id text(200)
    -> AttributeFilter
Edif_Servico_Social_point (reader MDB_ADO_1) [off]
    attributes: OBJECTID autonumber, SHAPE oleobject, geometriaAproximada long, offSetSimbX single, orientacao single, tipoClasseCnae long, nome text(255), fkComplSvSoc text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Area_Edificada (reader MDB_ADO_1) [off]
    attributes: OBJECTID autonumber, SHAPE oleobject, controleId text(255), justTxt long, geometriaAproximada long, simbolizarCartaMini integer, fkClassificador text(255), obsAquisicao text(255), nomeAbrev text(255), tamanhoTxt single, offSetY single, offSetX single, nome text(255), controle_id text(200), SHAPE_Length double, SHAPE_Area double
    -> AttributeFilter
GDB_ColumnInfo (reader MDB_ADO_1) [off]
    attributes: TableName text(255), FieldName text(255), columnFlags long
    -> AttributeFilter
Elemento_Fisiog_Natural_line_SHAPE_Index (reader MDB_ADO_1) [off]
    attributes: IndexedObjectId long, MinGX long, MinGY long, MaxGX long, MaxGY long
    -> AttributeFilter
Edif_Industrial_point (reader MDB_ADO_1) [off]
    attributes: OBJECTID autonumber, SHAPE oleobject, geometriaAproximada long, offSetSimbX single, orientacao single, nome text(255), offSetY single, justTxt long, fkComplIndustria text(255), offSetX single, offSetSimbY single, chamine long, nomeAbrev text(255), matConstr long, operacional long, simbolizarCartaMini integer, tipoDivisaoCnae long, obsAquisicao text(255), controleId text(255), situacaoFisica long, escalaMaxSimbolizar long, fkClassificador text(255), controle_id text(200)
    -> AttributeFilter
Cemiterio_point_SHAPE_Index (reader MDB_ADO_1) [off]
    attributes: IndexedObjectId long, MinGX long, MinGY long, MaxGX long, MaxGY long
    -> AttributeFilter
Ponto_Inicio_Drenagem_SHAPE_Index (reader MDB_ADO_1) [off]
    attributes: IndexedObjectId long, MinGX long, MinGY long, MaxGX long, MaxGY long
    -> AttributeFilter
Ponto_Drenagem_SHAPE_Index (reader MDB_ADO_1) [off]
    attributes: IndexedObjectId long, MinGX long, MinGY long, MaxGX long, MaxGY long
    -> AttributeFilter
Edif_Religiosa_point (reader MDB_ADO_1) [off]
    attributes: OBJECTID autonumber, SHAPE oleobject, geometriaAproximada long, offSetSimbX single, orientacao single, religiao text(255), nome text(255), fkComplOrgRel text(255), offSetY single, justTxt long, offSetX single, offSetSimbY single, nomeAbrev text(255), matConstr long, operacional long, tipoEdifRelig long, simbolizarCartaMini integer, ensino long, obsAquisicao text(255), controleId text(255), situacaoFisica long, escalaMaxSimbolizar long, fkClassificador text(255), controle_id text(200)
    -> AttributeFilter
Ponto_Cotado_Altimetrico_SHAPE_Index (reader MDB_ADO_1) [off]
    attributes: IndexedObjectId long, MinGX long, MinGY long, MaxGX long, MaxGY long
    -> AttributeFilter
Est_Gerad_Energia_Eletr_polygon (reader MDB_ADO_1) [off]
    attributes: OBJECTID autonumber, SHAPE oleobject, geometriaAproximada long, offSetSimbX single, tipoEstGerad long, potenciaFiscalizadaKW single, fkComplGerEnEletr text(255), nome text(255), offSetY single, justTxt long, offSetX single, offSetSimbY single, nomeAbrev text(255), operacional long, codigoEstacao text(255), simbolizarCartaMini integer, destEnergElet long, potenciaOutorgadaKW single, obsAquisicao text(255), controleId text(255), situacaoFisica long, escalaMaxSimbolizar long, fkClassificador text(255), controle_id text(200), SHAPE_Length double, SHAPE_Area double
    -> AttributeFilter
Aglomerado_Rural_SHAPE_Index (reader MDB_ADO_1) [off]
    attributes: IndexedObjectId long, MinGX long, MinGY long, MaxGX long, MaxGY long
    -> AttributeFilter
Edif_Pub_Civil_polygon_SHAPE_Index (reader MDB_ADO_1) [off]
    attributes: IndexedObjectId long, MinGX long, MinGY long, MaxGX long, MaxGY long
    -> AttributeFilter
Banco_Areia_polygon_SHAPE_Index (reader MDB_ADO_1) [off]
    attributes: IndexedObjectId long, MinGX long, MinGY long, MaxGX long, MaxGY long
    -> AttributeFilter
Ponto_Rodoviario_Ferrov (reader MDB_ADO_1) [off]
    attributes: OBJECTID autonumber, SHAPE oleobject, fkClassificador text(255), obsAquisicao text(255), relacionado long, controleId text(255), geometriaAproximada long, simbolizarCartaMini integer, modalUso long, controle_id text(200)
    -> AttributeFilter
Comporta_line_SHAPE_Index (reader MDB_ADO_1) [off]
    attributes: IndexedObjectId long, MinGX long, MinGY long, MaxGX long, MaxGY long
    -> AttributeFilter
Area_Ext_Mineral_SHAPE_Index (reader MDB_ADO_1) [off]
    attributes: IndexedObjectId long, MinGX long, MinGY long, MaxGX long, MaxGY long
    -> AttributeFilter
Elemento_Fisiog_Natural_point_SHAPE_Index (reader MDB_ADO_1) [off]
    attributes: IndexedObjectId long, MinGX long, MinGY long, MaxGX long, MaxGY long
    -> AttributeFilter
Campo_Quadra_polygon_SHAPE_Index (reader MDB_ADO_1) [off]
    attributes: IndexedObjectId long, MinGX long, MinGY long, MaxGX long, MaxGY long
    -> AttributeFilter
Pista_Ponto_Pouso_polygon_SHAPE_Index (reader MDB_ADO_1) [off]
    attributes: IndexedObjectId long, MinGX long, MinGY long, MaxGX long, MaxGY long
    -> AttributeFilter
Edif_Servico_Social_point_SHAPE_Index (reader MDB_ADO_1) [off]
    attributes: IndexedObjectId long, MinGX long, MinGY long, MaxGX long, MaxGY long
    -> AttributeFilter
Edif_Religiosa_point_SHAPE_Index (reader MDB_ADO_1) [off]
    attributes: IndexedObjectId long, MinGX long, MinGY long, MaxGX long, MaxGY long
    -> AttributeFilter
Ilha_polygon_SHAPE_Index (reader MDB_ADO_1) [off]
    attributes: IndexedObjectId long, MinGX long, MinGY long, MaxGX long, MaxGY long
    -> AttributeFilter
Ponto_Drenagem (reader MDB_ADO_1) [off]
    attributes: OBJECTID autonumber, SHAPE oleobject, obsAquisicao text(255), fkClassificador text(255), simbolizarCartaMini integer, geometriaAproximada long, controleId text(255), relacionado long, controle_id text(200)
    -> AttributeFilter
Torre_Comunic (reader MDB_ADO_1) [off]
    attributes: OBJECTID autonumber, SHAPE oleobject, fkClassificador text(255), geometriaAproximada long, offSetSimbX single, alturaEstimada single, ovgd long, nome text(255), fkComplComunic text(255), offSetY single, justTxt long, offSetX single, offSetSimbY single, nomeAbrev text(255), operacional long, simbolizarCartaMini integer, obsAquisicao text(255), controleId text(255), escalaMaxSimbolizar long, situacaoFisica long, posicaoRelEdific long, controle_id text(200)
    -> AttributeFilter
Edif_Industrial_point_SHAPE_Index (reader MDB_ADO_1) [off]
    attributes: IndexedObjectId long, MinGX long, MinGY long, MaxGX long, MaxGY long
    -> AttributeFilter
Terreno_Exposto_SHAPE_Index (reader MDB_ADO_1) [off]
    attributes: IndexedObjectId long, MinGX long, MinGY long, MaxGX long, MaxGY long
    -> AttributeFilter
Pto_Est_Med_Fenomenos_SHAPE_Index (reader MDB_ADO_1) [off]
    attributes: IndexedObjectId long, MinGX long, MinGY long, MaxGX long, MaxGY long
    -> AttributeFilter
Arruamento_SHAPE_Index (reader MDB_ADO_1) [off]
    attributes: IndexedObjectId long, MinGX long, MinGY long, MaxGX long, MaxGY long
    -> AttributeFilter
Terreno_Suj_Inundacao_SHAPE_Index (reader MDB_ADO_1) [off]
    attributes: IndexedObjectId long, MinGX long, MinGY long, MaxGX long, MaxGY long
    -> AttributeFilter
Trecho_Drenagem_SHAPE_Index (reader MDB_ADO_1) [off]
    attributes: IndexedObjectId long, MinGX long, MinGY long, MaxGX long, MaxGY long
    -> AttributeFilter
Edif_Pub_Civil_point_SHAPE_Index (reader MDB_ADO_1) [off]
    attributes: IndexedObjectId long, MinGX long, MinGY long, MaxGX long, MaxGY long
    -> AttributeFilter
Edif_Ensino_polygon (reader MDB_ADO_1) [off]
    attributes: OBJECTID autonumber, SHAPE oleobject, geometriaAproximada long, offSetSimbX single, orientacao single, tipoClasseCnae long, fkComplOrgEnsino text(255), nome text(255), offSetY single, justTxt long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
Edif_Saneamento_point_SHAPE_Index (reader MDB_ADO_1) [off]
    attributes: IndexedObjectId long, MinGX long, MinGY long, MaxGX long, MaxGY long
    -> AttributeFilter
Campo (reader MDB_ADO_1) [off]
    attributes: OBJECTID autonumber, SHAPE oleobject, fkClassificador text(255), obsAquisicao text(255), ocorrenciaEm long, simbolizarCartaMini integer, controleId text(255), nomeAbrev text(255), geometriaAproximada long, tipoCampo long, nome text(255), controle_id text(200), SHAPE_Length double, SHAPE_Area double
    -> AttributeFilter
Trecho_Rodoviario_SHAPE_Index (reader MDB_ADO_1) [off]
    attributes: IndexedObjectId long, MinGX long, MinGY long, MaxGX long, MaxGY long
    -> AttributeFilter
Edif_Const_Lazer_polygon (reader MDB_ADO_1) [off]
    attributes: OBJECTID autonumber, SHAPE oleobject, geometriaAproximada long, offSetSimbX single, orientacao single, nome text(255), tipoEdifLazer long, fkComplLazer text(255), offSetY single, justTxt long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
GDB_SpatialRefs (reader MDB_ADO_1) [off]
    attributes: SRID autonumber, SRTEXT memo, FalseX double, FalseY double, XYUnits double, FalseZ double, ZUnits double, FalseM double, MUnits double, IsHighPrecision long, XYTolerance double, ZTolerance double, MTolerance double
    -> AttributeFilter
Fonte_Dagua_SHAPE_Index (reader MDB_ADO_1) [off]
    attributes: IndexedObjectId long, MinGX long, MinGY long, MaxGX long, MaxGY long
    -> AttributeFilter
Terreno_Exposto (reader MDB_ADO_1) [off]
    attributes: OBJECTID autonumber, SHAPE oleobject, fkClassificador text(255), obsAquisicao text(255), controleId text(255), geometriaAproximada long, simbolizarCartaMini integer, tipoTerrExp long, causaExposicao long, controle_id text(200), SHAPE_Length double, SHAPE_Area double
    -> AttributeFilter
Confluencia_SHAPE_Index (reader MDB_ADO_1) [off]
    attributes: IndexedObjectId long, MinGX long, MinGY long, MaxGX long, MaxGY long
    -> AttributeFilter
Cidade (reader MDB_ADO_1) [off]
    attributes: OBJECTID autonumber, SHAPE oleobject, geometriaAproximada long, offSetSimbX single, identificadorPosicGeo text(255), orientacao single, nome text(255), simbolizar integer, offSetY single, justTxt long, longitude single, offSetX single, offSetSimbY single, latitude single, nomeAbrev text(255), longitude_txt text(255), simbolizarCartaMini integer, tamanhoTxt single, latitude_txt text(255), obsAquisicao text(255), controleId text(255), fkClassificador text(255), tipoCidade long, controle_id text(200)
    -> AttributeFilter
Ponto_Duto_SHAPE_Index (reader MDB_ADO_1) [off]
    attributes: IndexedObjectId long, MinGX long, MinGY long, MaxGX long, MaxGY long
    -> AttributeFilter
Edif_Pub_Militar_polygon (reader MDB_ADO_1) [off]
    attributes: OBJECTID autonumber, SHAPE oleobject, geometriaAproximada long, fkComplMilitar text(255), offSetSimbX single, orientacao single, tipoEdif long, nome text(255), offSetY single, justTxt long, tipoUsoEdif long, offSetX single, offSetSimbY single, nomeAbrev text(255), matConstr long, operacional long, simbolizarCartaMini integer, obsAquisicao text(255), controleId text(255), situacaoFisica long, escalaMaxSimbolizar long, fkClassificador text(255), controle_id text(200), SHAPE_Length double, SHAPE_Area double
    -> AttributeFilter
Travessia_point (reader MDB_ADO_1) [off]
    attributes: OBJECTID autonumber, SHAPE oleobject, fkClassificador text(255), controleId text(255), justTxt long, orientacao single, offSetY single, nomeAbrev text(255), geometriaAproximada long, simbolizarCartaMini integer, tipoTravessia long, nome text(255), offSetX single, obsAquisicao text(255), controle_id text(200)
    -> AttributeFilter
Galeria_Bueiro_point_SHAPE_Index (reader MDB_ADO_1) [off]
    attributes: IndexedObjectId long, MinGX long, MinGY long, MaxGX long, MaxGY long
    -> AttributeFilter
Cerrado_Cerradao_SHAPE_Index (reader MDB_ADO_1) [off]
    attributes: IndexedObjectId long, MinGX long, MinGY long, MaxGX long, MaxGY long
    -> AttributeFilter
Area_Lazer_SHAPE_Index (reader MDB_ADO_1) [off]
    attributes: IndexedObjectId long, MinGX long, MinGY long, MaxGX long, MaxGY long
    -> AttributeFilter
GDB_Items_Shape_Index (reader MDB_ADO_1) [off]
    attributes: IndexedObjectId long, MinGX long, MinGY long, MaxGX long, MaxGY long
    -> AttributeFilter
T_1_PointErrors_Shape_Index (reader MDB_ADO_1) [off]
    attributes: IndexedObjectId long, MinGX long, MinGY long, MaxGX long, MaxGY long
    -> AttributeFilter
Grupo_Transform_Energ_point (reader MDB_ADO_1) [off]
    attributes: OBJECTID autonumber, SHAPE oleobject, justTxt long, geometriaAproximada long, offSetSimbX single, fkClassificador text(255), nomeAbrev text(255), obsAquisicao text(255), fkComplSubEnEletr text(255), offSetX single, escalaMaxSimbolizar long, controleId text(255), offSetY single, simbolizarCartaMini integer, nome text(255), offSetSimbY single, controle_id text(200)
    -> AttributeFilter
Arquibancada_point (reader MDB_ADO_1) [off]
    attributes: OBJECTID autonumber, SHAPE oleobject, geometriaAproximada long, offSetSimbX single, orientacao single, nome text(255), fkComplLazer text(255), offSetY single, justTxt long, offSetX single, offSetSimbY single, nomeAbrev text(255), matConstr long, operacional long, simbolizarCartaMini integer, obsAquisicao text(255), controleId text(255), situacaoFisica long, escalaMaxSimbolizar long, fkClassificador text(255), controle_id text(200)
    -> AttributeFilter
Grupo_Transform_Energ_point_SHAPE_Index (reader MDB_ADO_1) [off]
    attributes: IndexedObjectId long, MinGX long, MinGY long, MaxGX long, MaxGY long
    -> AttributeFilter
Banco_Areia_polygon (reader MDB_ADO_1) [off]
    attributes: OBJECTID autonumber, SHAPE oleobject, materialPredominante long, offSetX single, justTxt long, nomeAbrev text(255), simbolizarCartaMini integer, controleId text(255), situacaoEmAgua long, nome text(255), obsAquisicao text(255), tipoBanco long, fkClassificador text(255), offSetY single, geometriaAproximada long, controle_id text(200), SHAPE_Length double, SHAPE_Area double
    -> AttributeFilter
T_1_PointErrors (reader MDB_ADO_1) [off]
    attributes: ObjectID autonumber, OriginClassID long, OriginID long, DestClassID long, DestID long, TopoRuleType long, TopoRuleID long, Shape oleobject, IsException long
    -> AttributeFilter
Entroncamento_SHAPE_Index (reader MDB_ADO_1) [off]
    attributes: IndexedObjectId long, MinGX long, MinGY long, MaxGX long, MaxGY long
    -> AttributeFilter
T_1_LineErrors_Shape_Index (reader MDB_ADO_1) [off]
    attributes: IndexedObjectId long, MinGX long, MinGY long, MaxGX long, MaxGY long
    -> AttributeFilter

Bookmark: New Bookmark
Veg_Cultivada_SHAPE_Index00 (writer MDB_ADO_4)
    attributes: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
Trecho_Energia_SHAPE_Index (writer MDB_ADO_4)
    attributes: IndexedObjectId long, MinGX long, MinGY long, MaxGX long, MaxGY long
Trecho_Drenagem (writer MDB_ADO_4)
    attributes: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
Rocha_polygon_SHAPE_Index (writer MDB_ADO_4)
    attributes: IndexedObjectId long, MinGX long, MinGY long, MaxGX long, MaxGY long
Travessia_point_SHAPE_Index (writer MDB_ADO_4)
    attributes: IndexedObjectId long, MinGX long, MinGY long, MaxGX long, MaxGY long
Area_Uso_Comunitario_point (writer MDB_ADO_4)
    attributes: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
Ponto_Inicio_Drenagem (writer MDB_ADO_4)
    attributes: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
Edif_Saude_point_SHAPE_Index (writer MDB_ADO_4)
    attributes: IndexedObjectId long, MinGX long, MinGY long, MaxGX long, MaxGY long
Deposito_Geral_polygon_SHAPE_Index (writer MDB_ADO_4)
    attributes: IndexedObjectId long, MinGX long, MinGY long, MaxGX long, MaxGY long
Rocha_polygon (writer MDB_ADO_4)
    attributes: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
Campo_SHAPE_Index (writer MDB_ADO_4)
    attributes: IndexedObjectId long, MinGX long, MinGY long, MaxGX long, MaxGY long
Campo_Quadra_point_SHAPE_Index (writer MDB_ADO_4)
    attributes: IndexedObjectId long, MinGX long, MinGY long, MaxGX long, MaxGY long
Alter_Fisiog_Antropica_line (writer MDB_ADO_4)
    attributes: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
Edif_Agrop_Ext_Veg_Pesca_point_SHAPE_Index (writer MDB_ADO_4)
    attributes: IndexedObjectId long, MinGX long, MinGY long, MaxGX long, MaxGY long
Atracadouro_polygon (writer MDB_ADO_4)
    attributes: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
Edif_Rodoviaria_polygon (writer MDB_ADO_4)
    attributes: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
Trecho_Rodoviario (writer MDB_ADO_4)
    attributes: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
Delimitacao_Fisica (writer MDB_ADO_4)
    attributes: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
Ponto_Duto (writer MDB_ADO_4)
    attributes: OBJECTID autonumber, SHAPE oleobject, obsAquisicao text(255), fkClassificador text(255), simbolizarCartaMini integer, geometriaAproximada long, controleId text(255), relacionado long, controle_id text(200)
Trecho_Massa_Dagua_SHAPE_Index (writer MDB_ADO_4)
    attributes: IndexedObjectId long, MinGX long, MinGY long, MaxGX long, MaxGY long
Edif_Const_Lazer_point_SHAPE_Index (writer MDB_ADO_4)
    attributes: IndexedObjectId long, MinGX long, MinGY long, MaxGX long, MaxGY long
Antena_Comunic (writer MDB_ADO_4)
    attributes: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
T_1_PolyErrors (writer MDB_ADO_4)
    attributes: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
Barragem_line_SHAPE_Index (writer MDB_ADO_4)
    attributes: IndexedObjectId long, MinGX long, MinGY long, MaxGX long, MaxGY long
Arruamento (writer MDB_ADO_4)
    attributes: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
Edif_Comerc_Serv_polygon_SHAPE_Index (writer MDB_ADO_4)
    attributes: IndexedObjectId long, MinGX long, MinGY long, MaxGX long, MaxGY long
Edif_Pub_Militar_polygon_SHAPE_Index (writer MDB_ADO_4)
    attributes: IndexedObjectId long, MinGX long, MinGY long, MaxGX long, MaxGY long
Trecho_Energia (writer MDB_ADO_4)
    attributes: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
Edif_Const_Turistica_point (writer MDB_ADO_4)
    attributes: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
Cemiterio_polygon (writer MDB_ADO_4)
    attributes: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
Caatinga (writer MDB_ADO_4)
    attributes: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
Dep_Saneamento_polygon (writer MDB_ADO_4)
    attributes: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
Identific_Trecho_Rod (writer MDB_ADO_4)
    attributes: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
Arquibancada_point_SHAPE_Index (writer MDB_ADO_4)
    attributes: IndexedObjectId long, MinGX long, MinGY long, MaxGX long, MaxGY long
Edif_Ext_Mineral_polygon_SHAPE_Index (writer MDB_ADO_4)
    attributes: IndexedObjectId long, MinGX long, MinGY long, MaxGX long, MaxGY long
Trilha_Picada_SHAPE_Index (writer MDB_ADO_4)
    attributes: IndexedObjectId long, MinGX long, MinGY long, MaxGX long, MaxGY long
Edif_Servico_Social_polygon_SHAPE_Index (writer MDB_ADO_4)
    attributes: IndexedObjectId long, MinGX long, MinGY long, MaxGX long, MaxGY long
Barragem_line (writer MDB_ADO_4)
    attributes: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
Edif_Habitacional_point (writer MDB_ADO_4)
    attributes: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
Edif_Const_Aeroportuaria_point_SHAPE_Index (writer MDB_ADO_4)
    attributes: IndexedObjectId long, MinGX long, MinGY long, MaxGX long, MaxGY long
Edif_Const_Turistica_point_SHAPE_Index (writer MDB_ADO_4)
    attributes: IndexedObjectId long, MinGX long, MinGY long, MaxGX long, MaxGY long
T_1_DirtyAreas (writer MDB_ADO_4)
    attributes: ObjectID autonumber, IsRetired long, DirtyArea oleobject, DirtyArea_Length double, DirtyArea_Area double
Atracadouro_polygon_SHAPE_Index (writer MDB_ADO_4)
    attributes: IndexedObjectId long, MinGX long, MinGY long, MaxGX long, MaxGY long
Cemiterio_polygon_SHAPE_Index (writer MDB_ADO_4)
    attributes: IndexedObjectId long, MinGX long, MinGY long, MaxGX long, MaxGY long
Caatinga_SHAPE_Index (writer MDB_ADO_4)
    attributes: IndexedObjectId long, MinGX long, MinGY long, MaxGX long, MaxGY long
Cemiterio_point (writer MDB_ADO_4)
    attributes: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
Ponto_Trecho_Energia_SHAPE_Index (writer MDB_ADO_4)
    attributes: IndexedObjectId long, MinGX long, MinGY long, MaxGX long, MaxGY long
Area_Energia_Eletrica_SHAPE_Index (writer MDB_ADO_4)
    attributes: IndexedObjectId long, MinGX long, MinGY long, MaxGX long, MaxGY long
Sumidouro_Vertedouro_SHAPE_Index (writer MDB_ADO_4)
    attributes: IndexedObjectId long, MinGX long, MinGY long, MaxGX long, MaxGY long
Edif_Servico_Social_polygon (writer MDB_ADO_4)
    attributes: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
Edif_Constr_Est_Med_point_SHAPE_Index (writer MDB_ADO_4)
    attributes: IndexedObjectId long, MinGX long, MinGY long, MaxGX long, MaxGY long
Deposito_Geral_polygon (writer MDB_ADO_4)
    attributes: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
GDB_ItemTypes (writer MDB_ADO_4)
    attributes: ObjectID autonumber, UUID replicationid, ParentTypeID replicationid, Name text(160)
Edif_Ensino_point_SHAPE_Index (writer MDB_ADO_4)
    attributes: IndexedObjectId long, MinGX long, MinGY long, MaxGX long, MaxGY long
Ponto_Cotado_Altimetrico (writer MDB_ADO_4)
    attributes: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
Edif_Saude_polygon_SHAPE_Index (writer MDB_ADO_4)
    attributes: IndexedObjectId long, MinGX long, MinGY long, MaxGX long, MaxGY long
Edif_Pub_Militar_point_SHAPE_Index (writer MDB_ADO_4)
    attributes: IndexedObjectId long, MinGX long, MinGY long, MaxGX long, MaxGY long
Edif_Pub_Civil_polygon (writer MDB_ADO_4)
    attributes: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
Veg_Cultivada_SHAPE_Index (writer MDB_ADO_4)
    attributes: IndexedObjectId long, MinGX long, MinGY long, MaxGX long, MaxGY long
Veg_Cultivada (writer MDB_ADO_4)
    attributes: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
GDB_DatabaseLocks (writer MDB_ADO_4)
    attributes: LockID autonumber, LockType long, UserName memo, MachineName memo
Edif_Ensino_point (writer MDB_ADO_4)
    attributes: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
Cidade_SHAPE_Index (writer MDB_ADO_4)
    attributes: IndexedObjectId long, MinGX long, MinGY long, MaxGX long, MaxGY long
Identific_Trecho_Rod_SHAPE_Index (writer MDB_ADO_4)
    attributes: IndexedObjectId long, MinGX long, MinGY long, MaxGX long, MaxGY long
Pista_Competicao_line_SHAPE_Index (writer MDB_ADO_4)
    attributes: IndexedObjectId long, MinGX long, MinGY long, MaxGX long, MaxGY long
Edif_Const_Lazer_polygon_SHAPE_Index (writer MDB_ADO_4)
    attributes: IndexedObjectId long, MinGX long, MinGY long, MaxGX long, MaxGY long
Edif_Const_Lazer_point (writer MDB_ADO_4)
    attributes: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
GDB_GeomColumns (writer MDB_ADO_4)
    attributes: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
Patio_polygon_SHAPE_Index (writer MDB_ADO_4)
    attributes: IndexedObjectId long, MinGX long, MinGY long, MaxGX long, MaxGY long
Trecho_Duto_SHAPE_Index (writer MDB_ADO_4)
    attributes: IndexedObjectId long, MinGX long, MinGY long, MaxGX long, MaxGY long
T_1_PolyErrors_Shape_Index (writer MDB_ADO_4)
    attributes: IndexedObjectId long, MinGX long, MinGY long, MaxGX long, MaxGY long
Comporta_line (writer MDB_ADO_4)
    attributes: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
Elemento_Fisiog_Natural_point (writer MDB_ADO_4)
    attributes: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
Edif_Ext_Mineral_point (writer MDB_ADO_4)
    attributes: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
Massa_Dagua (writer MDB_ADO_4)
    attributes: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
Trecho_Massa_Dagua (writer MDB_ADO_4)
    attributes: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
GDB_ItemRelationshipTypes (writer MDB_ADO_4)
    attributes: ObjectID autonumber, UUID replicationid, OrigItemTypeID replicationid, DestItemTypeID replicationid, Name text(160), ForwardLabel text(255), BackwardLabel text(255), IsContainment integer
T_1_DirtyAreas_DirtyArea_Index (writer MDB_ADO_4)
    attributes: IndexedObjectId long, MinGX long, MinGY long, MaxGX long, MaxGY long
Dep_Abast_Agua_point_SHAPE_Index (writer MDB_ADO_4)
    attributes: IndexedObjectId long, MinGX long, MinGY long, MaxGX long, MaxGY long
Ponto_Trecho_Energia (writer MDB_ADO_4)
    attributes: OBJECTID autonumber, SHAPE oleobject, obsAquisicao text(255), fkClassificador text(255), simbolizarCartaMini integer, geometriaAproximada long, controleId text(255), tipoPtoEnergia long, controle_id text(200)
Cerrado_Cerradao (writer MDB_ADO_4)
    attributes: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
Curva_Nivel (writer MDB_ADO_4)
    attributes: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
Edif_Saneamento_point (writer MDB_ADO_4)
    attributes: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
Patio_polygon (writer MDB_ADO_4)
    attributes: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
Entroncamento (writer MDB_ADO_4)
    attributes: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
Dep_Saneamento_point (writer MDB_ADO_4)
    attributes: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
Edif_Comerc_Serv_point (writer MDB_ADO_4)
    attributes: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
Selections (writer MDB_ADO_4)
    attributes: SelectionID autonumber, TargetName text(255)
Nome_Local_SHAPE_Index (writer MDB_ADO_4)
    attributes: IndexedObjectId long, MinGX long, MinGY long, MaxGX long, MaxGY long
Edif_Pub_Civil_point (writer MDB_ADO_4)
    attributes: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
GDB_Items (writer MDB_ADO_4)
    attributes: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
Atracadouro_point_SHAPE_Index (writer MDB_ADO_4)
    attributes: IndexedObjectId long, MinGX long, MinGY long, MaxGX long, MaxGY long
Edif_Constr_Est_Med_point (writer MDB_ADO_4)
    attributes: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
Campo_Quadra_polygon (writer MDB_ADO_4)
    attributes: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
Posto_Combustivel_point_SHAPE_Index (writer MDB_ADO_4)
    attributes: IndexedObjectId long, MinGX long, MinGY long, MaxGX long, MaxGY long
Edif_Comerc_Serv_polygon (writer MDB_ADO_4)
    attributes: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
Edif_Rodoviaria_point_SHAPE_Index (writer MDB_ADO_4)
    attributes: IndexedObjectId long, MinGX long, MinGY long, MaxGX long, MaxGY long
Ponte_point (writer MDB_ADO_4)
    attributes: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
Trilha_Picada (writer MDB_ADO_4)
    attributes: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
Edif_Const_Aeroportuaria_point (writer MDB_ADO_4)
    attributes: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
Area_Industrial (writer MDB_ADO_4)
    attributes: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
Edif_Religiosa_polygon_SHAPE_Index (writer MDB_ADO_4)
    attributes: IndexedObjectId long, MinGX long, MinGY long, MaxGX long, MaxGY long
Deposito_Geral_point_SHAPE_Index (writer MDB_ADO_4)
    attributes: IndexedObjectId long, MinGX long, MinGY long, MaxGX long, MaxGY long
Torre_Comunic_SHAPE_Index (writer MDB_ADO_4)
    attributes: IndexedObjectId long, MinGX long, MinGY long, MaxGX long, MaxGY long
Limite_Massa_Dagua (writer MDB_ADO_4)
    attributes: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
Edif_Rodoviaria_polygon_SHAPE_Index (writer MDB_ADO_4)
    attributes: IndexedObjectId long, MinGX long, MinGY long, MaxGX long, MaxGY long
Sumidouro_Vertedouro (writer MDB_ADO_4)
    attributes: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
Edif_Pub_Militar_point (writer MDB_ADO_4)
    attributes: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
Ilha_polygon (writer MDB_ADO_4)
    attributes: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
GDB_ReplicaLog (writer MDB_ADO_4)
    attributes: ID autonumber, ReplicaID long, Event long, ErrorCode long, LogDate datetime, SourceBeginGen long, SourceEndGen long, TargetGen long
Galeria_Bueiro_point (writer MDB_ADO_4)
    attributes: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
Deposito_Geral_point (writer MDB_ADO_4)
    attributes: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
Edif_Ensino_polygon_SHAPE_Index (writer MDB_ADO_4)
    attributes: IndexedObjectId long, MinGX long, MinGY long, MaxGX long, MaxGY long
Edif_Comerc_Serv_point_SHAPE_Index (writer MDB_ADO_4)
    attributes: IndexedObjectId long, MinGX long, MinGY long, MaxGX long, MaxGY long
Edif_Ext_Mineral_polygon (writer MDB_ADO_4)
    attributes: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
Alter_Fisiog_Antropica_line_SHAPE_Index (writer MDB_ADO_4)
    attributes: IndexedObjectId long, MinGX long, MinGY long, MaxGX long, MaxGY long
T_1_LineErrors (writer MDB_ADO_4)
    attributes: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
Campo_Quadra_point (writer MDB_ADO_4)
    attributes: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
Edif_Industrial_polygon (writer MDB_ADO_4)
    attributes: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
Pto_Est_Med_Fenomenos (writer MDB_ADO_4)
    attributes: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
Gruta_Caverna_point_SHAPE_Index (writer MDB_ADO_4)
    attributes: IndexedObjectId long, MinGX long, MinGY long, MaxGX long, MaxGY long
Pista_Competicao_line (writer MDB_ADO_4)
    attributes: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
Edif_Habitacional_point_SHAPE_Index (writer MDB_ADO_4)
    attributes: IndexedObjectId long, MinGX long, MinGY long, MaxGX long, MaxGY long
Edif_Abast_Agua_point_SHAPE_Index (writer MDB_ADO_4)
    attributes: IndexedObjectId long, MinGX long, MinGY long, MaxGX long, MaxGY long
Nome_Local (writer MDB_ADO_4)
    attributes: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
Delimitacao_Fisica_SHAPE_Index (writer MDB_ADO_4)
    attributes: IndexedObjectId long, MinGX long, MinGY long, MaxGX long, MaxGY long
Edif_Ext_Mineral_point_SHAPE_Index (writer MDB_ADO_4)
    attributes: IndexedObjectId long, MinGX long, MinGY long, MaxGX long, MaxGY long
Limite_Massa_Dagua_SHAPE_Index (writer MDB_ADO_4)
    attributes: IndexedObjectId long, MinGX long, MinGY long, MaxGX long, MaxGY long
Ponto_Rodoviario_Ferrov_SHAPE_Index (writer MDB_ADO_4)
    attributes: IndexedObjectId long, MinGX long, MinGY long, MaxGX long, MaxGY long
Confluencia (writer MDB_ADO_4)
    attributes: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
Posto_Combustivel_point (writer MDB_ADO_4)
    attributes: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
Edif_Comunic_point_SHAPE_Index (writer MDB_ADO_4)
    attributes: IndexedObjectId long, MinGX long, MinGY long, MaxGX long, MaxGY long
Edif_Comunic_point (writer MDB_ADO_4)
    attributes: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
GDB_ItemRelationships (writer MDB_ADO_4)
    attributes: ObjectID autonumber, UUID replicationid, OriginID replicationid, DestID replicationid, Type replicationid, Attributes memo, Properties long
Gruta_Caverna_point (writer MDB_ADO_4)
    attributes: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
Area_Energia_Eletrica (writer MDB_ADO_4)
    attributes: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
Edif_Religiosa_polygon (writer MDB_ADO_4)
    attributes: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
Edif_Industrial_polygon_SHAPE_Index (writer MDB_ADO_4)
    attributes: IndexedObjectId long, MinGX long, MinGY long, MaxGX long, MaxGY long
Edif_Abast_Agua_point (writer MDB_ADO_4)
    attributes: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
Dep_Saneamento_polygon_SHAPE_Index (writer MDB_ADO_4)
    attributes: IndexedObjectId long, MinGX long, MinGY long, MaxGX long, MaxGY long
Area_Uso_Comunitario_point_SHAPE_Index (writer MDB_ADO_4)
    attributes: IndexedObjectId long, MinGX long, MinGY long, MaxGX long, MaxGY long
Edif_Saude_point (writer MDB_ADO_4)
    attributes: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
Area_Industrial_SHAPE_Index (writer MDB_ADO_4)
    attributes: IndexedObjectId long, MinGX long, MinGY long, MaxGX long, MaxGY long
Edif_Saude_polygon (writer MDB_ADO_4)
    attributes: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
Est_Gerad_Energia_Eletr_polygon_SHAPE_Index (writer MDB_ADO_4)
    attributes: IndexedObjectId long, MinGX long, MinGY long, MaxGX long, MaxGY long
Area_Lazer (writer MDB_ADO_4)
    attributes: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
Atracadouro_point (writer MDB_ADO_4)
    attributes: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
Trecho_Duto (writer MDB_ADO_4)
    attributes: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
Ponte_point_SHAPE_Index (writer MDB_ADO_4)
    attributes: IndexedObjectId long, MinGX long, MinGY long, MaxGX long, MaxGY long
Antena_Comunic_SHAPE_Index (writer MDB_ADO_4)
    attributes: IndexedObjectId long, MinGX long, MinGY long, MaxGX long, MaxGY long
Edif_Agrop_Ext_Veg_Pesca_point (writer MDB_ADO_4)
    attributes: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
Area_Ext_Mineral (writer MDB_ADO_4)
    attributes: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
Massa_Dagua_SHAPE_Index (writer MDB_ADO_4)
    attributes: IndexedObjectId long, MinGX long, MinGY long, MaxGX long, MaxGY long
Aglomerado_Rural (writer MDB_ADO_4)
    attributes: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
Elemento_Fisiog_Natural_line (writer MDB_ADO_4)
    attributes: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
Pista_Ponto_Pouso_polygon (writer MDB_ADO_4)
    attributes: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
Fonte_Dagua (writer MDB_ADO_4)
    attributes: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
Curva_Nivel_SHAPE_Index (writer MDB_ADO_4)
    attributes: IndexedObjectId long, MinGX long, MinGY long, MaxGX long, MaxGY long
Dep_Saneamento_point_SHAPE_Index (writer MDB_ADO_4)
    attributes: IndexedObjectId long, MinGX long, MinGY long, MaxGX long, MaxGY long
SelectedObjects (writer MDB_ADO_4)
    attributes: SelectionID long, ObjectID long
Area_Edificada_SHAPE_Index (writer MDB_ADO_4)
    attributes: IndexedObjectId long, MinGX long, MinGY long, MaxGX long, MaxGY long
Terreno_Suj_Inundacao (writer MDB_ADO_4)
    attributes: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
Edif_Rodoviaria_point (writer MDB_ADO_4)
    attributes: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
Edif_Servico_Social_point (writer MDB_ADO_4)
    attributes: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
Area_Edificada (writer MDB_ADO_4)
    attributes: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
GDB_ColumnInfo (writer MDB_ADO_4)
    attributes: TableName text(255), FieldName text(255), columnFlags long
Elemento_Fisiog_Natural_line_SHAPE_Index (writer MDB_ADO_4)
    attributes: IndexedObjectId long, MinGX long, MinGY long, MaxGX long, MaxGY long
Edif_Industrial_point (writer MDB_ADO_4)
    attributes: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
Cemiterio_point_SHAPE_Index (writer MDB_ADO_4)
    attributes: IndexedObjectId long, MinGX long, MinGY long, MaxGX long, MaxGY long
Ponto_Inicio_Drenagem_SHAPE_Index (writer MDB_ADO_4)
    attributes: IndexedObjectId long, MinGX long, MinGY long, MaxGX long, MaxGY long
Ponto_Drenagem_SHAPE_Index (writer MDB_ADO_4)
    attributes: IndexedObjectId long, MinGX long, MinGY long, MaxGX long, MaxGY long
Edif_Religiosa_point (writer MDB_ADO_4)
    attributes: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
Ponto_Cotado_Altimetrico_SHAPE_Index (writer MDB_ADO_4)
    attributes: IndexedObjectId long, MinGX long, MinGY long, MaxGX long, MaxGY long
Est_Gerad_Energia_Eletr_polygon (writer MDB_ADO_4)
    attributes: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
Aglomerado_Rural_SHAPE_Index (writer MDB_ADO_4)
    attributes: IndexedObjectId long, MinGX long, MinGY long, MaxGX long, MaxGY long
Edif_Pub_Civil_polygon_SHAPE_Index (writer MDB_ADO_4)
    attributes: IndexedObjectId long, MinGX long, MinGY long, MaxGX long, MaxGY long
Banco_Areia_polygon_SHAPE_Index (writer MDB_ADO_4)
    attributes: IndexedObjectId long, MinGX long, MinGY long, MaxGX long, MaxGY long
Ponto_Rodoviario_Ferrov (writer MDB_ADO_4)
    attributes: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
Comporta_line_SHAPE_Index (writer MDB_ADO_4)
    attributes: IndexedObjectId long, MinGX long, MinGY long, MaxGX long, MaxGY long
Area_Ext_Mineral_SHAPE_Index (writer MDB_ADO_4)
    attributes: IndexedObjectId long, MinGX long, MinGY long, MaxGX long, MaxGY long
Elemento_Fisiog_Natural_point_SHAPE_Index (writer MDB_ADO_4)
    attributes: IndexedObjectId long, MinGX long, MinGY long, MaxGX long, MaxGY long
Campo_Quadra_polygon_SHAPE_Index (writer MDB_ADO_4)
    attributes: IndexedObjectId long, MinGX long, MinGY long, MaxGX long, MaxGY long
Pista_Ponto_Pouso_polygon_SHAPE_Index (writer MDB_ADO_4)
    attributes: IndexedObjectId long, MinGX long, MinGY long, MaxGX long, MaxGY long
Edif_Servico_Social_point_SHAPE_Index (writer MDB_ADO_4)
    attributes: IndexedObjectId long, MinGX long, MinGY long, MaxGX long, MaxGY long
Edif_Religiosa_point_SHAPE_Index (writer MDB_ADO_4)
    attributes: IndexedObjectId long, MinGX long, MinGY long, MaxGX long, MaxGY long
Ilha_polygon_SHAPE_Index (writer MDB_ADO_4)
    attributes: IndexedObjectId long, MinGX long, MinGY long, MaxGX long, MaxGY long
Ponto_Drenagem (writer MDB_ADO_4)
    attributes: OBJECTID autonumber, SHAPE oleobject, obsAquisicao text(255), fkClassificador text(255), simbolizarCartaMini integer, geometriaAproximada long, controleId text(255), relacionado long, controle_id text(200)
Torre_Comunic (writer MDB_ADO_4)
    attributes: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
Edif_Industrial_point_SHAPE_Index (writer MDB_ADO_4)
    attributes: IndexedObjectId long, MinGX long, MinGY long, MaxGX long, MaxGY long
Terreno_Exposto_SHAPE_Index (writer MDB_ADO_4)
    attributes: IndexedObjectId long, MinGX long, MinGY long, MaxGX long, MaxGY long
Pto_Est_Med_Fenomenos_SHAPE_Index (writer MDB_ADO_4)
    attributes: IndexedObjectId long, MinGX long, MinGY long, MaxGX long, MaxGY long
Arruamento_SHAPE_Index (writer MDB_ADO_4)
    attributes: IndexedObjectId long, MinGX long, MinGY long, MaxGX long, MaxGY long
Terreno_Suj_Inundacao_SHAPE_Index (writer MDB_ADO_4)
    attributes: IndexedObjectId long, MinGX long, MinGY long, MaxGX long, MaxGY long
Trecho_Drenagem_SHAPE_Index (writer MDB_ADO_4)
    attributes: IndexedObjectId long, MinGX long, MinGY long, MaxGX long, MaxGY long
Edif_Pub_Civil_point_SHAPE_Index (writer MDB_ADO_4)
    attributes: IndexedObjectId long, MinGX long, MinGY long, MaxGX long, MaxGY long
Edif_Ensino_polygon (writer MDB_ADO_4)
    attributes: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
Edif_Saneamento_point_SHAPE_Index (writer MDB_ADO_4)
    attributes: IndexedObjectId long, MinGX long, MinGY long, MaxGX long, MaxGY long
Campo (writer MDB_ADO_4)
    attributes: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
Trecho_Rodoviario_SHAPE_Index (writer MDB_ADO_4)
    attributes: IndexedObjectId long, MinGX long, MinGY long, MaxGX long, MaxGY long
Edif_Const_Lazer_polygon (writer MDB_ADO_4)
    attributes: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
GDB_SpatialRefs (writer MDB_ADO_4)
    attributes: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
Fonte_Dagua_SHAPE_Index (writer MDB_ADO_4)
    attributes: IndexedObjectId long, MinGX long, MinGY long, MaxGX long, MaxGY long
Terreno_Exposto (writer MDB_ADO_4)
    attributes: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
Confluencia_SHAPE_Index (writer MDB_ADO_4)
    attributes: IndexedObjectId long, MinGX long, MinGY long, MaxGX long, MaxGY long
Cidade (writer MDB_ADO_4)
    attributes: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
Ponto_Duto_SHAPE_Index (writer MDB_ADO_4)
    attributes: IndexedObjectId long, MinGX long, MinGY long, MaxGX long, MaxGY long
Edif_Pub_Militar_polygon (writer MDB_ADO_4)
    attributes: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
Travessia_point (writer MDB_ADO_4)
    attributes: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
Galeria_Bueiro_point_SHAPE_Index (writer MDB_ADO_4)
    attributes: IndexedObjectId long, MinGX long, MinGY long, MaxGX long, MaxGY long
Cerrado_Cerradao_SHAPE_Index (writer MDB_ADO_4)
    attributes: IndexedObjectId long, MinGX long, MinGY long, MaxGX long, MaxGY long
Area_Lazer_SHAPE_Index (writer MDB_ADO_4)
    attributes: IndexedObjectId long, MinGX long, MinGY long, MaxGX long, MaxGY long
GDB_Items_Shape_Index (writer MDB_ADO_4)
    attributes: IndexedObjectId long, MinGX long, MinGY long, MaxGX long, MaxGY long
T_1_PointErrors_Shape_Index (writer MDB_ADO_4)
    attributes: IndexedObjectId long, MinGX long, MinGY long, MaxGX long, MaxGY long
Grupo_Transform_Energ_point (writer MDB_ADO_4)
    attributes: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
Arquibancada_point (writer MDB_ADO_4)
    attributes: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
Grupo_Transform_Energ_point_SHAPE_Index (writer MDB_ADO_4)
    attributes: IndexedObjectId long, MinGX long, MinGY long, MaxGX long, MaxGY long
Banco_Areia_polygon (writer MDB_ADO_4)
    attributes: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
T_1_PointErrors (writer MDB_ADO_4)
    attributes: ObjectID autonumber, OriginClassID long, OriginID long, DestClassID long, DestID long, TopoRuleType long, TopoRuleID long, Shape oleobject, IsException long
Entroncamento_SHAPE_Index (writer MDB_ADO_4)
    attributes: IndexedObjectId long, MinGX long, MinGY long, MaxGX long, MaxGY long
T_1_LineErrors_Shape_Index (writer MDB_ADO_4)
    attributes: IndexedObjectId long, MinGX long, MinGY long, MaxGX long, MaxGY long
