FME workspace gerar_area_aparir_deLimitadores_centroidesV1.0.0FME2022.1.fmw

Parameters:
- SourceDataset_POSTGIS = r_1292-3-NO   # Database
- FEATURE_TYPES = edgv.aux_insumo_externo_a edgv.aux_insumo_externo_l edgv.aux_insumo_externo_p edgv.aux_moldura_a edgv.aux_moldura_area_continua_a edgv.elemnat_toponimo_fisiografico_natural_l edgv.elemnat_toponimo_fisiografico_natural_p edgv.infra_mobilidade_urbana_l edgv.aux_reambulacao_a edgv.aux_reambulacao_l edgv.aux_reambulacao_p edgv.aux_revisao_a edgv.aux_revisao_l edgv.aux_revisao_p edgv.aux_validacao_a edgv.aux_validacao_l edgv.aux_validacao_p edgv.centroide_area_construida_p edgv.centroide_area_sem_dados_p edgv.centroide_elemento_hidrografico_p edgv.centroide_ilha_p edgv.centroide_limite_especial_p edgv.centroide_massa_dagua_p edgv.centroide_vegetacao_p edgv.cobter_area_construida_a edgv.cobter_massa_dagua_a edgv.cobter_vegetacao_a edgv.constr_area_uso_especifico_a edgv.constr_deposito_a edgv.constr_deposito_p edgv.constr_edificacao_a edgv.constr_edificacao_p edgv.constr_extracao_mineral_a edgv.constr_extracao_mineral_p edgv.constr_ocupacao_solo_a edgv.constr_ocupacao_solo_l edgv.constr_ocupacao_solo_p edgv.delimitador_area_construida_l edgv.delimitador_area_sem_dados_l edgv.delimitador_elemento_hidrografico_l edgv.delimitador_limite_especial_l edgv.delimitador_massa_dagua_l edgv.delimitador_vegetacao_l edgv.edicao_area_sem_dados_a edgv.edicao_borda_elemento_hidrografico_l edgv.edicao_grid_edicao_l edgv.edicao_identificador_trecho_rod_p edgv.edicao_limite_especial_l edgv.edicao_limite_legal_l edgv.edicao_ponto_mudanca_p edgv.edicao_simb_area_p edgv.edicao_simb_cota_mestra_l edgv.edicao_simb_direcao_corrente_p edgv.edicao_simb_torre_energia_p edgv.edicao_simb_vegetacao_p edgv.edicao_texto_generico_l edgv.edicao_texto_generico_p edgv.elemnat_curva_nivel_l edgv.elemnat_elemento_fisiografico_a edgv.elemnat_elemento_fisiografico_l edgv.elemnat_elemento_fisiografico_p edgv.elemnat_elemento_hidrografico_a edgv.elemnat_elemento_hidrografico_l edgv.elemnat_elemento_hidrografico_p edgv.elemnat_ilha_a edgv.elemnat_ilha_p edgv.elemnat_ponto_cotado_p edgv.elemnat_sumidouro_vertedouro_p edgv.elemnat_terreno_sujeito_inundacao_a edgv.elemnat_trecho_drenagem_l edgv.infra_alteracao_fisiografica_antropica_l edgv.infra_barragem_a edgv.infra_barragem_l edgv.infra_elemento_energia_a edgv.infra_elemento_energia_l edgv.infra_elemento_energia_p edgv.infra_elemento_infraestrutura_a edgv.infra_elemento_infraestrutura_l edgv.infra_elemento_infraestrutura_p edgv.infra_elemento_viario_l edgv.infra_elemento_viario_p edgv.infra_ferrovia_l edgv.infra_pista_pouso_a edgv.infra_pista_pouso_l edgv.infra_pista_pouso_p edgv.infra_travessia_hidroviaria_l edgv.infra_trecho_duto_l edgv.infra_vala_l edgv.infra_via_deslocamento_l edgv.llp_delimitacao_fisica_l edgv.llp_limite_especial_a edgv.llp_localidade_p edgv.llp_pais_a edgv.llp_ponto_controle_p edgv.llp_unidade_federacao_a public.aux_grid_revisao_a public.aux_track_l public.aux_track_p public.sap_local
- SourceDataset_OGCGEOPACKAGE_3 = C:\Marcos_Batista\DGEO\REAMBULACAO\moldura.gpkg   # GeoPackage File
- SourceDataset_OGCGEOPACKAGE = C:\Marcos_Batista\DGEO\REAMBULACAO\lines_merge.gpkg   # GeoPackage File

Readers:
- POSTGIS_1: POSTGIS from $(SourceDataset_POSTGIS)
- OGCGEOPACKAGE_1: OGCGEOPACKAGE from $(SourceDataset_OGCGEOPACKAGE)
- OGCGEOPACKAGE_2: OGCGEOPACKAGE from $(SourceDataset_OGCGEOPACKAGE_3)

moldura (reader OGCGEOPACKAGE_2)
    attributes: id text, nome text(255), mi text(255), inom text(255), observacao text(255), operador_criacao text(255), data_criacao datetime, operador_atualizacao text(255), data_atualizacao datetime, area_otf double, fid int,PrimaryKey
    -> Reprojector_2
    -> Reprojector
Reprojector_2
    DEST = SIRGAS2000.UTM-24S
    INTERPOLATION_TYPE_NAME = Nearest Neighbor
    RASTER_CELL_SIZE = Preserve Cells
    RASTER_TOLERANCE = 0.0
    REPROJECTED -> moldura
    REPROJECTED -> AttributeKeeper
AttributeKeeper
    CREATE_BULK_MODE_FEATURES = NO
    KEEP_ATTRS = mi
    -> Clipper [CANDIDATE]
moldura: Inspector
lines_merge (reader OGCGEOPACKAGE_1)
    attributes: id text, observacao text(255), operador_criacao text(255), data_criacao datetime, operador_atualizacao text(255), data_atualizacao datetime, length_otf double, nome text(255), tipo mediumint, texto_edicao text(255), label_x double, label_y double, justificativa_txt mediumint, visivel mediumint, situacao_em_poligono mediumint, regime mediumint, tamanho_txt double, posicao_rotulo mediumint, direcao_fixada mediumint, material_construcao mediumint, sobreposto_transportes mediumint, largura_simbologia double, situacao_fisica mediumint, posicao_relativa mediumint, nr_linhas mediumint, eletrificada mediumint, bitola mediumint, em_arruamento mediumint, jurisdicao mediumint, administracao mediumint,
      concessionaria text(255), revestimento mediumint, trafego mediumint, nr_faixas text(255), nr_pistas text(255), canteiro_divisorio mediumint, sigla text(255), ordem_simbologia mediumint, layer text, path text, fid int,PrimaryKey
    -> lines_merge
    -> Tester_4
Tester_4
    BOOL_OP = AND
    TEST_CLAUSE:
      TEST @Value(layer) = infra_via_deslocamento_l
      TEST @Value(tipo) = 5
    TEST_MODE = TEST
    PASSED -> Arruamento
    FAILED -> Reprojector
Arruamento: Inspector [off]
Reprojector
    DEST = SIRGAS2000.UTM-24S
    INTERPOLATION_TYPE_NAME = Nearest Neighbor
    RASTER_CELL_SIZE = Preserve Cells
    RASTER_TOLERANCE = 0.0
    REPROJECTED -> Snapper
Snapper
    CLEANING_TOLERANCE = Automatic
    SNAPTYPE = ALL
    TOLERANCE = 5
    SNAPPED -> Junction_2
    UNTOUCHED -> Junction_2
Junction_2
    -> Remover_linhas_sem_saidas_2 [Intersector_Input]
    -> Junction_2_Output
Junction_2_Output: Inspector [off]
Remover_linhas_sem_saidas_2
    -> AttributeKeeper_2
AttributeKeeper_2
    CREATE_BULK_MODE_FEATURES = NO
    -> Counter
Counter
    CNT_ATTR = _id_segmento
    DOMAIN = counter
    SCOPE = Global
    START = 1
    -> Remover_linhas_sem_saidas_2_Output
    -> Intersector_2
    -> Bufferer [off]
    -> ClosedCurveFilter
ClosedCurveFilter
    CHECK_NODE_ELEVATION = Yes
    CLOSED -> ClosedCurveFilter_Closed
    OPEN -> Bufferer
ClosedCurveFilter_Closed: Inspector
Bufferer
    ANGLE = 22.5
    CAP_STYLE = Square
    CORNER_STYLE = Miter
    MITER_LIMIT = 1
    MODE = AREA
    OFFSET = 0.01
    OFFSET_UNITS = METERS
    PRECISION = APPROX
    BUFFERED -> Dissolver
    BUFFERED -> Clipper_2 [CLIPPER]
Dissolver
    ACCUM_INPUT_ATTRS = Use Attributes From One Feature
    CLEANING_TOLERANCE = Automatic
    CONNECT_Z_MODE = First Wins
    DEAGGREGATE_INPUT = Yes
    AREA -> Clipper [CLIPPER]
    AREA -> Dissolver_Area
Dissolver_Area: Inspector [off]
Clipper
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Clipper_Inside
    OUTSIDE -> Intersector
Clipper_Inside: Inspector [off]
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> Intersector_Intersected
    INTERSECTED -> GeometryCoercer
    NODE -> Intersector_Node
GeometryCoercer
    GQUERY:
      for $geom in //geometry
      where $geom/count(parent::geometry) = 0
      return number($geom/@fme_id)
    KIND = fme_polygon
    COERCED -> Bufferer_2
Bufferer_2
    ANGLE = 22.5
    CAP_STYLE = Square
    CORNER_STYLE = Bevel
    MODE = AREA
    OFFSET = 0.01
    OFFSET_UNITS = NONE
    PRECISION = APPROX
    BUFFERED -> Snapper_2
Snapper_2
    EXTEND_LINES = ALWAYS
    SAVE_SHORT_LINES = No
    SNAPTYPE = VERTEX
    TOLERANCE = 2
    SNAPPED -> AttributeKeeper_3
    UNTOUCHED -> AttributeKeeper_3
AttributeKeeper_3
    CREATE_BULK_MODE_FEATURES = NO
    KEEP_ATTRS = mi
    -> Counter_2
Counter_2
    CNT_ATTR = _id_areas
    DOMAIN = counter
    SCOPE = Global
    START = 0
    -> Areas_segmento
    -> LineOnAreaOverlayer [AREA]
Areas_segmento: Inspector
Intersector_Intersected: Inspector [off]
Intersector_Node: Inspector [off]
Intersector_2
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> AttributeKeeper_5
    NODE -> Bufferer_3
AttributeKeeper_5
    CREATE_BULK_MODE_FEATURES = NO
    KEEP_ATTRS = _id_segmento
    -> Segmentos
    -> NeighborPairFinder [CANDIDATE]
    -> LineOnAreaOverlayer [LINE]
    -> Intersector_3
Segmentos: Inspector
LineOnAreaOverlayer [off]
    CLEANING_TOLERANCE = Automatic
    DEAGGREGATE_INPUT = Yes
    OV_ATTR = _overlaps_Area_line_seg
    LINE -> LineOnAreaOverlayer_Line
    AREA -> LineOnAreaOverlayer_Area
    COLLAPSED -> LineOnAreaOverlayer_Collapsed
    <REJECTED> -> LineOnAreaOverlayer__Rejected_
LineOnAreaOverlayer_Line: Inspector
LineOnAreaOverlayer_Area: Inspector
LineOnAreaOverlayer_Collapsed: Inspector
LineOnAreaOverlayer__Rejected_: Inspector
Bufferer_3
    ANGLE = 22.5
    CAP_STYLE = Arc
    CORNER_STYLE = Arc
    MODE = AREA
    OFFSET = 1
    OFFSET_UNITS = NONE
    PRECISION = APPROX
    BUFFERED -> Bufferer_3_Buffered
    BUFFERED -> Clipper_2 [CANDIDATE]
    BUFFERED -> LineOnAreaOverlayer_2 [AREA]
    BUFFERED -> Intersector_3
Intersector_3
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> LineOnAreaOverlayer_2 [LINE]
LineOnAreaOverlayer_2
    CLEANING_TOLERANCE = Automatic
    DEAGGREGATE_INPUT = Yes
    OV_ATTR = _overlaps
    LINE -> LineOnAreaOverlayer_2_Line
    AREA -> LineOnAreaOverlayer_2_Area
LineOnAreaOverlayer_2_Line: Inspector
LineOnAreaOverlayer_2_Area: Inspector
Bufferer_3_Buffered: Inspector [off]
Clipper_2
    BOUNDARY_CASES = INSIDE
    CLEANING_TOLERANCE = Automatic
    CLIPPED_ATTR = _clipped
    CLIPPERS_FIRST = NO
    GENERATE_LIST = YES
    INVALID_PARTS_HANDLING = REJECT_WHOLE
    LIST_ATTRS_TO_INCLUDE = _id_segmento
    LIST_NAME = _id_seg
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    OUTSIDE -> Deaggregator
Deaggregator
    ATTR_ACCUM_MODE = Merge List Attributes
    ATTR_CONFLICT_RES = Use List Attribute Values
    EXPLODE_INSTANCES = No
    GEOM_NAME_FIELD = _geometry_name
    LIST_ATTR_MODE_LOOKUP = LEAN
    MODE = Flatten One Level
    PART_NUMBER_FIELD = _part_number
    SPLIT_COMPOSITES = No
    DEAGGREGATED -> AttributeKeeper_4
AttributeKeeper_4
    CREATE_BULK_MODE_FEATURES = NO
    KEEP_ATTRS = _node_number,_part_number
    -> Angulos
    -> CenterPointReplacer
CenterPointReplacer
    POINTTYPE = CENTER
    POINT -> NeighborPairFinder [BASE]
NeighborPairFinder
    KEYATTR = _id_segmento
    MAX = 1
    MINANGLE = 0
    MODE = Bases and Candidates
    MATCHED -> NeighborPairFinder_MatchedBase
    UNMATCHED_BASE -> NeighborPairFinder_UnmatchedBase
    CLOSEST_VECTOR -> NeighborPairFinder_ClosestVector
    SECOND_CLOSEST_VECTOR -> NeighborPairFinder_SecondClosestVector
    <REJECTED> -> NeighborPairFinder__Rejected_
NeighborPairFinder_MatchedBase: Inspector
NeighborPairFinder_UnmatchedBase: Inspector
NeighborPairFinder_ClosestVector: Inspector
NeighborPairFinder_SecondClosestVector: Inspector
NeighborPairFinder__Rejected_: Inspector
Angulos: Inspector
Remover_linhas_sem_saidas_2_Output: Inspector [off]
lines_merge: Inspector [off]
aux_insumo_externo_a (reader POSTGIS_1) [off]
    attributes: id uuid, nome varchar(255), fonte varchar(255), observacao varchar(255), operador_criacao varchar(255), data_criacao timestamptz, operador_atualizacao varchar(255), data_atualizacao timestamptz, espacamento float4, inom varchar(255), justificativa_txt int2, label_x float4, label_y float4, mi varchar(255), situacao_fisica int2, tamanho_txt float4, texto_edicao varchar(255), tipo int2, visivel int2
    -> _All_
    -> FeatureTypeFilter
_All_: Inspector [off]
FeatureTypeFilter [off]
    ATTRIBUTES = <Blank>,<Unfiltered>,edgv.centroide_area_construida_p,edgv.centroide_area_sem_dados_p,edgv.centroide_elemento_hidrografico_p,edgv.centroide_ilha_p,edgv.centroide_limite_especial_p,edgv.centroide_massa_dagua_p,edgv.centroide_vegetacao_p,edgv.delimitador_area_construida_l,edgv.delimitador_area_sem_dados_l,edgv.delimitador_elemento_hidrografico_l,edgv.delimitador_limite_especial_l,edgv.delimitador_massa_dagua_l,edgv.delimitador_vegetacao_l,edgv.aux_moldura_a,edgv.elemnat_trecho_drenagem_l,edgv.infra_barragem_l,edgv.infra_vala_l,edgv.infra_via_deslocamento_l,edgv.infra_ferrovia_l
    edgv.centroide_area_construida_p -> Classes
    edgv.centroide_area_sem_dados_p -> Classes
    edgv.centroide_elemento_hidrografico_p -> Classes
    edgv.centroide_ilha_p -> Classes
    edgv.centroide_limite_especial_p -> Classes
    edgv.centroide_massa_dagua_p -> Classes
    edgv.centroide_vegetacao_p -> Classes
    edgv.delimitador_area_construida_l -> Classes
    edgv.delimitador_area_construida_l -> Area_Edificada [CLIPPER]
    edgv.delimitador_area_sem_dados_l -> Classes
    edgv.delimitador_area_sem_dados_l -> Junction
    edgv.delimitador_elemento_hidrografico_l -> Classes
    edgv.delimitador_elemento_hidrografico_l -> Junction
    edgv.delimitador_limite_especial_l -> Classes
    edgv.delimitador_limite_especial_l -> Junction
    edgv.delimitador_massa_dagua_l -> Classes
    edgv.delimitador_massa_dagua_l -> Massa_Dagua [CLIPPER]
    edgv.delimitador_vegetacao_l -> Classes
    edgv.delimitador_vegetacao_l -> Junction
    edgv.aux_moldura_a -> Classes
    edgv.aux_moldura_a -> Area_Edificada [CANDIDATE]
    edgv.elemnat_trecho_drenagem_l -> Classes
    edgv.elemnat_trecho_drenagem_l -> Junction
    edgv.infra_barragem_l -> Classes
    edgv.infra_barragem_l -> Massa_Dagua [CLIPPER]
    edgv.infra_vala_l -> Classes
    edgv.infra_vala_l -> Junction
    edgv.infra_via_deslocamento_l -> Tester
    edgv.infra_via_deslocamento_l -> Classes
    edgv.infra_via_deslocamento_l -> Junction
    edgv.infra_ferrovia_l -> Classes
    edgv.infra_ferrovia_l -> Junction
Classes: Inspector [off]
    TACKATTRS = fme_feature_type
Junction [off]
    -> Vegetacao [CLIPPER]
Area_Edificada: Clipper [off]
    ATTR_ACCUM_MODE = MERGE
    ATTR_CONFLICT_RES = CLIPPER
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Area_Edificada_Inside
    OUTSIDE -> Massa_Dagua [CANDIDATE]
Massa_Dagua: Clipper [off]
    ATTR_ACCUM_MODE = MERGE
    ATTR_CONFLICT_RES = CLIPPER
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Massa_Dagua_Inside
    OUTSIDE -> Vegetacao [CANDIDATE]
Vegetacao: Clipper
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> Vegetacao_Inside
    OUTSIDE -> Vegetacao_Outside
Vegetacao_Inside: Inspector
Vegetacao_Outside: Inspector
Massa_Dagua_Inside: Inspector
Area_Edificada_Inside: Inspector
Tester [off]
    BOOL_OP = OR
    TEST_CLAUSE = TEST @Value(tipo) != 5
    TEST_MODE = TEST
    PASSED -> FeatureTypeFilter_edgv.infra_via_deslocamento_l
FeatureTypeFilter_edgv.infra_via_deslocamento_l: Inspector
