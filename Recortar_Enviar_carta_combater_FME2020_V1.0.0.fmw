FME workspace Recortar_Enviar_carta_combater_FME2020_V1.0.0.fmw

Parameters:
- SourceDataset_POSTGIS = combater_PE_2022   # Database
- DestDataset_POSTGIS = combater_PE_2022   # Database
- SourceDataset_POSTGIS_2 = Molduras   # Database
- MI = 1446-2-NO
- EPSG_DESTINO = EPSG:31984
- FEATURE_TYPES = base.curva_nivel_l base.estrada_l base.ferrovia_l base.limite_estadual_l base.limite_municipal_l base.nome_local_p base.penhasco_l base.ponte_l base.ponto_urbano_p base.rio_l base.tunel_l public.aux_moldura_a public.aux_obj_area_a public.aux_obj_linha_l public.aux_obj_ponto_p public.raster_columns
- FEATURE_TYPES_2 = public.molduras_50k

Readers:
- POSTGIS_1: POSTGIS from $(SourceDataset_POSTGIS)
- POSTGIS_3: POSTGIS from $(SourceDataset_POSTGIS_2)

Writers:
- POSTGIS_2: POSTGIS to $(DestDataset_POSTGIS)

Note: : Molduras [POSTGIS] 50k
molduras_50k (reader POSTGIS_3)
    attributes: mi text,PrimaryKey, inom text, nome_carta text, estado text, ligacao_n text, ligacao_ne text, ligacao_l text, ligacao_se text, ligacao_s text, ligacao_so text, ligacao_o text, ligacao_no text
    -> Reprojector_3
Reprojector_3
    DEST = $(EPSG_DESTINO)
    INTERPOLATION_TYPE_NAME = Nearest Neighbor
    RASTER_CELL_SIZE = Preserve Cells
    RASTER_TOLERANCE = 0.0
    SOURCE = Read from feature
    REPROJECTED -> Tester_2
Tester_2
    BOOL_OP = OR
    COMPOSITE_TEST = 1
    TEST_CLAUSE = TEST @Value(mi) = $(MI)
    TEST_MODE = TEST
    PASSED -> Clipper [CLIPPER]
cob_ter_a (reader POSTGIS_1)
    attributes: id serial,PrimaryKey, codigo int4, tipo varchar(25), nome varchar(60), descricao varchar(80), label_ocultar int2, label_espac_letras int2, label_espac_palavra int2, label_posicao int2, label_tam int2, aq_fim date, aq_ini date, aq_respvl varchar(15), area_cont_fim date, area_cont_ini date, area_cont_respvl varchar(15), blocksize_x int4, blocksize_y int4, carta_nome varchar(40), cota int4, ed_fim date, ed_ini date, ed_respvl varchar(15), estado1 varchar(80), estado2 varchar(80), label_espac_palavras int2, mestra varchar(1), mi char(10), municipio1 varchar(80), municipio2 varchar(80),
      nodata_values text, num_bands int4, out_db text, pixel_types text, r_raster_column text, r_table_catalog text, r_table_name text, r_table_schema text, regular_blocking bool, same_alignment bool, scale_x float8, scale_y float8, simb_deslc varchar(45), simb_ocultar int2, simb_rot int2, spatial_index bool, srid int4, val_fim date, val_ini date, val_respvl varchar(15)
    -> Reprojector_2
Reprojector_2
    DEST = $(EPSG_DESTINO)
    INTERPOLATION_TYPE_NAME = Nearest Neighbor
    RASTER_CELL_SIZE = Preserve Cells
    RASTER_TOLERANCE = 0.0
    SOURCE = Read from feature
    REPROJECTED -> Tester
Tester
    BOOL_OP = OR
    COMPOSITE_TEST = 1
    TEST_CLAUSE = TEST @StringLength($(MI)) > 4
    TEST_MODE = TEST
    PASSED -> Clipper [CLIPPEE]
    FAILED -> Tester_Failed
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Aggregator
Aggregator
    ACCUM_ATTRS_NAME = Use Attributes From One Feature
    AGGREGATE_TYPE = Homogeneous Collection (If Possible)
    GROUP_BY = fme_feature_type id
    MODE = Geometry - Assemble One Level
    SEP = ,
    AGGREGATE -> Deaggregator_2
Deaggregator_2
    EXPLODE_INSTANCES = No
    GEOM_NAME_FIELD = _geometry_name
    LIST_ATTR_MODE_LOOKUP = LEAN
    MODE = Flatten All Levels
    SPLIT_COMPOSITES = No
    DEAGGREGATED -> UUIDGenerator
UUIDGenerator
    UUID_ATTR = _uuid
    -> Aggregator_2
Aggregator_2
    ACCUM_ATTRS_NAME = Use Attributes From One Feature
    AGGREGATE_TYPE = Homogeneous Collection (If Possible)
    GROUP_BY = fme_feature_type _uuid
    MODE = Geometry - Assemble One Level
    SEP = ,
    AGGREGATE -> AggregateFilter
AggregateFilter
    AGGREGATE -> Counter
    NOT_AGGREGATE -> NAO_ADD
Counter
    CNT_ATTR = _count
    DOMAIN = @Value(fme_feature_type)
    SCOPE = Global
    START = 1
    -> AttributeCreator
AttributeCreator
    ATTR_TABLE = SET_TO id = @Value(_count)
    -> cob_ter_a (writer POSTGIS_2)
cob_ter_a (writer POSTGIS_2)
    attributes: id serial,PrimaryKey, codigo int4, tipo varchar(25), nome varchar(60), descricao varchar(80), label_ocultar int2, label_espac_letras int2, label_espac_palavra int2, label_posicao int2, label_tam int2, aq_fim date, aq_ini date, aq_respvl varchar(15), area_cont_fim date, area_cont_ini date, area_cont_respvl varchar(15), blocksize_x int4, blocksize_y int4, carta_nome varchar(40), cota int4, ed_fim date, ed_ini date, ed_respvl varchar(15), estado1 varchar(80), estado2 varchar(80), label_espac_palavras int2, mestra varchar(1), mi char(10), municipio1 varchar(80), municipio2 varchar(80),
      nodata_values text, num_bands int4, out_db text, pixel_types text, r_raster_column text, r_table_catalog text, r_table_name text, r_table_schema text, regular_blocking bool, same_alignment bool, scale_x float8, scale_y float8, simb_deslc varchar(45), simb_ocultar int2, simb_rot int2, spatial_index bool, srid int4, val_fim date, val_ini date, val_respvl varchar(15)
NAO_ADD: Inspector
Tester_Failed: Inspector
