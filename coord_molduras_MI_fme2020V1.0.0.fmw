FME workspace coord_molduras_MI_fme2020V1.0.0.fmw

Parameters:
- SourceDataset_POSTGIS = Controle_PE   # Database
- DestDataset_HTML = $(FME_MF_DIR)Insumos\html\coord_moldaras_mi_25k.html   # HTML Files(*.html)|*.html Destination Html File
- SourceDataset_SHAPEFILE = ""C:\Marcos_Batista\PostGis\MI Fusos Shp\MI_Moldura_Gothic_18.shp" "C:\Marcos_Batista\PostGis\MI Fusos Shp\MI_Moldura_Gothic_19.shp" "C:\Marcos_Batista\PostGis\MI Fusos Shp\MI_Moldura_Gothic_20.shp" "C:\Marcos_Batista\PostGis\MI Fusos Shp\MI_Moldura_Gothic_21.shp" "C:\Marcos_Batista\PostGis\MI Fusos Shp\MI_Moldura_Gothic_22.shp" "C:\Marcos_Batista\PostGis\MI Fusos Shp\MI_Moldura_Gothic_23.shp" "C:\Marcos_Batista\PostGis\MI Fusos Shp\MI_Moldura_Gothic_24.shp" "C:\Marcos_Batista\PostGis\MI Fusos Shp\MI_Moldura_Gothic_25.shp""   # Source Esri Shapefile(s)
- FEATURE_TYPES =
- casas_decimais = 8

Readers:
- POSTGIS_1: POSTGIS from $(SourceDataset_POSTGIS)
- SHAPEFILE_1: SHAPEFILE from $(SourceDataset_SHAPEFILE)

Writers:
- HTML_1: HTML to $(DestDataset_HTML)

MI_Moldura_Gothic_18 (reader SHAPEFILE_1)
    attributes: MI char(254), Ind_Nomen char(254), _fuso char(200), inom char(80), mi_1 char(80)
    -> Tester
Tester
    BOOL_OP = OR
    COMPOSITE_TEST = 1
    TEST_CLAUSE = TEST MI ATTRIBUTE_HAS_A_VALUE ""
    TEST_MODE = TEST
    PASSED -> Reprojector_2
Reprojector_2
    DEST = EPSG:4674
    INTERPOLATION_TYPE_NAME = Nearest Neighbor
    RASTER_CELL_SIZE = Preserve Cells
    RASTER_TOLERANCE = 0.0
    SOURCE = Read from feature
    REPROJECTED -> AttributeManager
AttributeManager
    ATTR_TABLE:
      RENAME_SET_VALUE MI > mi
      REMOVE Ind_Nomen
      RENAME_SET_VALUE _fuso > fuso
      REMOVE mi_1
    -> GeometryExtractor
    -> AttributeCreator_4
AttributeCreator_4
    ATTR_TABLE:
      SET_TO mi = @ReplaceString(@Value(mi),@Right(@Value(mi),4),@Left(@Right(@Value(mi),4), 1))
      SET_TO inom = @ReplaceString(@Value(inom),@Right(@Value(mi),4),@Left(@Right(@Value(mi),4), 1))
    -> Aggregator
Aggregator
    ACCUM_ATTRS_NAME = Use Attributes From One Feature
    AGGREGATE_TYPE = Homogeneous Collection (If Possible)
    GROUP_BY = mi
    MODE = Geometry - Assemble One Level
    SEP = ,
    AGGREGATE -> Dissolver
Dissolver
    ACCUM_INPUT_ATTRS = Use Attributes From One Feature
    CLEANING_TOLERANCE = Automatic
    CONNECT_Z_MODE = First Wins
    DEAGGREGATE_INPUT = Yes
    GROUP_BY = mi
    AREA -> GeometryExtractor
    AREA -> AttributeCreator_5
AttributeCreator_5
    ATTR_TABLE:
      SET_TO mi = @ReplaceString(@Value(mi),@Right(@Value(mi),3),@Left(@Right(@Value(mi),3), 1))
      SET_TO inom = @ReplaceString(@Value(inom),@Right(@Value(mi),3),@Left(@Right(@Value(mi),3), 1))
    -> Aggregator_2
Aggregator_2
    ACCUM_ATTRS_NAME = Use Attributes From One Feature
    AGGREGATE_TYPE = Homogeneous Collection (If Possible)
    GROUP_BY = mi
    MODE = Geometry - Assemble One Level
    SEP = ,
    AGGREGATE -> Dissolver_2
Note: 100k
Dissolver_2
    ACCUM_INPUT_ATTRS = Use Attributes From One Feature
    CLEANING_TOLERANCE = Automatic
    CONNECT_Z_MODE = First Wins
    DEAGGREGATE_INPUT = Yes
    GROUP_BY = mi
    AREA -> GeometryExtractor
cartas (reader POSTGIS_1) [off]
    attributes: id serial,PrimaryKey, mi text, bloco int2, status numeric(1000,500), servidor text, niveis text, densidade int4, nome_carta text, inom text, total_obj int4, total_p int4, total_l int4, total_a int4, txt_p int4, txt_l int4, txt_a int4, regiao text, linha int2, coluna int2, escala text, ligacao_o text, ligacao_s text, ligacao_se text, ligacao_so text, ligacao_l text, ligacao_n text, ligacao_no text, ligacao_ne text, impressa bool, ligacao bool,
      preparador int4, inicio_preparo timestamp, termino_preparo timestamp, aqtra int4, inicio_aq_tra timestamp, termino_aq_tra timestamp, aqhid int4, inicio_aq_hid timestamp, termino_aq_hid timestamp, aqcorterr int4, inicio_aq_corterr timestamp, termino_aq_corterr timestamp, revisor int4, inicio_revisao timestamp, termino_revisao timestamp, validacao int4, inicio_validacao timestamp, termino_validacao timestamp
    -> GeometryExtractor
GeometryExtractor
    ATTR = _geometry
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> CenterPointReplacer
CenterPointReplacer
    POINTTYPE = CENTER
    POINT -> PointOnAreaOverlayer [POINT]
fusos (reader POSTGIS_1) [off]
    attributes: id int8,PrimaryKey, ogc_fid int8, nome varchar(80), fuso int8, mc int8, epsg varchar(80), src varchar(80)
    -> AttributeKeeper
AttributeKeeper
    KEEP_ATTRS = epsg,fuso,src
    -> PointOnAreaOverlayer [AREA]
Note: 25K
PointOnAreaOverlayer
    ATTR_ACCUM_MODE = Merge Incoming
    ATTR_CONFLICT_RES = Use Original
    DEAGGREGATE_INPUT = Yes
    OV_ATTR = _overlaps
    POLYS_FIRST = NO
    POINT -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> AttributeCreator
    -> AttributeCreator_3
AttributeCreator [off]
    ATTR_TABLE:
      SET_TO epsg = EPSG:4674
      SET_TO mi = @Left(@Value(mi),6)
    -> Reprojector
    -> Bufferer
AttributeCreator_3
    ATTR_TABLE = SET_TO epsg = EPSG:4674
    -> Bufferer
    -> Reprojector
Reprojector [off]
    DEST = @Value(epsg)
    INTERPOLATION_TYPE_NAME = Nearest Neighbor
    RASTER_CELL_SIZE = Preserve Cells
    RASTER_TOLERANCE = 0.0
    SOURCE = Read from feature
    REPROJECTED -> Bufferer
Bufferer
    ANGLE = 22.5
    CAP_STYLE = None
    CORNER_STYLE = Miter
    MITER_LIMIT = 1
    MODE = AREA
    OFFSET = 2000
    OFFSET_UNITS = METERS
    PRECISION = APPROX
    BUFFERED -> BoundsExtractor
Note: 50k
BoundsExtractor
    XMAX = _xmax
    XMIN = _xmin
    YMAX = _ymax
    YMIN = _ymin
    ZMAX = _zmax
    ZMIN = _zmin
    -> AttributeKeeper_2
AttributeKeeper_2
    KEEP_ATTRS = epsg,mi,_xmax,_xmin,_ymax,_ymin,fuso,inom
    -> AttributeCreator_2
AttributeCreator_2
    ATTR_TABLE:
      SET_TO coord = @round(@Value(_xmin),$(casas_decimais)) @round(@Value(_ymax),$(casas_decimais)), @round(@Value(_xmax),$(casas_decimais)) @round(@Value(_ymax),$(casas_decimais)), @round(@Value(_xmax),$(casas_decimais)) @round(@Value(_ymin),$(casas_decimais)), @round(@Value(_xmin),$(casas_decimais)) @round(@Value(_ymin),$(casas_decimais)), @round(@Value(_xmin),$(casas_decimais)) @round(@Value(_ymax),$(casas_decimais))
      SET_TO array_html = Lista_MI.update({'@Value(mi)' : {'coord' : '@Value(coord)', 'epsg' : '@Value(epsg)', 'fuso' : @Value(fuso), 'inom' : '@Value(inom)'}})<br>
    -> MIs
    -> Sorter
MIs: Inspector
Sorter
    SORT_PARM = mi ALPHA ASCENDING
    SORTED -> AttributeKeeper_3
AttributeKeeper_3
    KEEP_ATTRS = array_html
    -> HTML (writer HTML_1)
HTML (writer HTML_1)
    attributes: html_content buffer
